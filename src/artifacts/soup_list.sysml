package memo_artifacts_soup_list {
    private import ScalarValues::*;

            private import memo_artifacts_definitions::*;
            private import memo_core_enumerations::*;

            part def SoupList specializes ArtifactKindDef {
    attribute :>> documentTitle = "SOUP List (Software of Unknown Provenance)";
    attribute :>> regulatoryRef = "IEC 62304:2006 §8.1.2";
    attribute :>> artifactKind = ArtifactKind::soupList;
            }
}
