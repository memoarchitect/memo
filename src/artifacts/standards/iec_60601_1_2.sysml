// IEC 60601-1-2:2014+AMD1:2020 — collateral standard for electromagnetic
// disturbances.
//
// Separate from the 60601-1 pack because it is a separate designation with its
// own edition and amendment history: a hardware requirement claiming EMC
// emissions cites this document, not the general standard.
package memo_artifacts_standards_iec_60601_1_2 {
    private import ScalarValues::*;
    private import memo_core_enumerations::*;
    private import memo_core_relationships::*;
    private import memo_artifacts_standards_traceability::*;

    private import memo_core_common::*;
    part iec60601_1_2 : RegulatoryStandard {
        @MemoIdentity { :>> providedId = "STD-IEC-60601-1-2-COLLATERAL"; }
        attribute :>> designation = "IEC 60601-1-2:2014+AMD1:2020";
        attribute :>> edition = "4.1";
        attribute :>> issuer = "IEC";
        attribute :>> amendments = "AMD1:2020";
        attribute :>> appliesToRegime = (RegulatoryRegimeKind::CE, RegulatoryRegimeKind::MDR, RegulatoryRegimeKind::UKCA, RegulatoryRegimeKind::FDA_510k, RegulatoryRegimeKind::FDA_PMA);
        part iec60601_1_2Clause4 : StandardClause {
            @MemoIdentity { :>> providedId = "STD-IEC-60601-1-2-4"; }
            attribute :>> clauseNumber = "4";
            attribute :>> title = "general requirements for electromagnetic disturbances";
            attribute :>> normativeStrength = "shall";
        }
        part iec60601_1_2Clause5 : StandardClause {
            @MemoIdentity { :>> providedId = "STD-IEC-60601-1-2-5"; }
            attribute :>> clauseNumber = "5";
            attribute :>> title = "electromagnetic compatibility information in accompanying documents";
            attribute :>> normativeStrength = "shall";
        }
        part iec60601_1_2Clause7 : StandardClause {
            @MemoIdentity { :>> providedId = "STD-IEC-60601-1-2-7"; }
            attribute :>> clauseNumber = "7";
            attribute :>> title = "electromagnetic emissions";
            attribute :>> normativeStrength = "shall";
        }
        part iec60601_1_2Clause8 : StandardClause {
            @MemoIdentity { :>> providedId = "STD-IEC-60601-1-2-8"; }
            attribute :>> clauseNumber = "8";
            attribute :>> title = "electromagnetic immunity";
            attribute :>> normativeStrength = "shall";
        }
    }


}
