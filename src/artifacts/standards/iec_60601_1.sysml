// IEC 60601-1:2005+AMD1:2012+AMD2:2020 — basic safety and essential
// performance of medical electrical equipment.
//
// This pack is the test of whether the standards library generalises past
// software: 60601-1 is a hardware-and-system standard, so its clauses are
// claimed by hardware requirements, physical elements and system-level
// documents rather than by software items.
//
// Depth is representative — the clause level, plus the sub-clauses MEMO
// documents actually claim. `title` is a MEMO-AUTHORED scope phrase, never
// the standard's own normative wording.
package memo_artifacts_standards_iec_60601_1 {
    private import ScalarValues::*;
    private import memo_core_enumerations::*;
    private import memo_core_relationships::*;
    private import memo_artifacts_standards_traceability::*;

    private import memo_core_common::*;
    part iec60601_1 : RegulatoryStandard {
        @MemoIdentity { :>> providedId = "STD-IEC-60601-1"; }
        attribute :>> designation = "IEC 60601-1:2005+AMD1:2012+AMD2:2020";
        attribute :>> edition = "3.2";
        attribute :>> issuer = "IEC";
        attribute :>> appliesToRegime = (RegulatoryRegimeKind::CE, RegulatoryRegimeKind::MDR, RegulatoryRegimeKind::UKCA, RegulatoryRegimeKind::FDA_510k, RegulatoryRegimeKind::FDA_PMA);
        part iec60601_1Clause4 : StandardClause {
            @MemoIdentity { :>> providedId = "STD-IEC-60601-1-4"; }
            attribute :>> clauseNumber = "4";
            attribute :>> title = "general requirements for basic safety and essential performance";
            attribute :>> normativeStrength = "shall";
            part iec60601_1Clause4_2 : StandardClause {
                @MemoIdentity { :>> providedId = "STD-IEC-60601-1-4-2"; }
                attribute :>> clauseNumber = "4.2";
                attribute :>> title = "risk management process for medical electrical equipment";
                attribute :>> normativeStrength = "shall";
            }
            part iec60601_1Clause4_3 : StandardClause {
                @MemoIdentity { :>> providedId = "STD-IEC-60601-1-4-3"; }
                attribute :>> clauseNumber = "4.3";
                attribute :>> title = "essential performance identification";
                attribute :>> normativeStrength = "shall";
            }
        }
        part iec60601_1Clause5 : StandardClause {
            @MemoIdentity { :>> providedId = "STD-IEC-60601-1-5"; }
            attribute :>> clauseNumber = "5";
            attribute :>> title = "general requirements for testing";
            attribute :>> normativeStrength = "shall";
        }
        part iec60601_1Clause7 : StandardClause {
            @MemoIdentity { :>> providedId = "STD-IEC-60601-1-7"; }
            attribute :>> clauseNumber = "7";
            attribute :>> title = "equipment identification, marking and accompanying documents";
            attribute :>> normativeStrength = "shall";
        }
        part iec60601_1Clause8 : StandardClause {
            @MemoIdentity { :>> providedId = "STD-IEC-60601-1-8"; }
            attribute :>> clauseNumber = "8";
            attribute :>> title = "protection against electrical hazards";
            attribute :>> normativeStrength = "shall";
        }
        part iec60601_1Clause9 : StandardClause {
            @MemoIdentity { :>> providedId = "STD-IEC-60601-1-9"; }
            attribute :>> clauseNumber = "9";
            attribute :>> title = "protection against mechanical hazards";
            attribute :>> normativeStrength = "shall";
        }
        part iec60601_1Clause10 : StandardClause {
            @MemoIdentity { :>> providedId = "STD-IEC-60601-1-10"; }
            attribute :>> clauseNumber = "10";
            attribute :>> title = "protection against unwanted and excessive radiation";
            attribute :>> normativeStrength = "shall";
        }
        part iec60601_1Clause11 : StandardClause {
            @MemoIdentity { :>> providedId = "STD-IEC-60601-1-11"; }
            attribute :>> clauseNumber = "11";
            attribute :>> title = "protection against excessive temperatures and related hazards";
            attribute :>> normativeStrength = "shall";
        }
        part iec60601_1Clause12 : StandardClause {
            @MemoIdentity { :>> providedId = "STD-IEC-60601-1-12"; }
            attribute :>> clauseNumber = "12";
            attribute :>> title = "accuracy of controls and protection against hazardous output";
            attribute :>> normativeStrength = "shall";
        }
        part iec60601_1Clause13 : StandardClause {
            @MemoIdentity { :>> providedId = "STD-IEC-60601-1-13"; }
            attribute :>> clauseNumber = "13";
            attribute :>> title = "hazardous situations and fault conditions";
            attribute :>> normativeStrength = "shall";
        }
        part iec60601_1Clause14 : StandardClause {
            @MemoIdentity { :>> providedId = "STD-IEC-60601-1-14"; }
            attribute :>> clauseNumber = "14";
            attribute :>> title = "programmable electrical medical systems";
            attribute :>> normativeStrength = "shall";
        }
        part iec60601_1Clause15 : StandardClause {
            @MemoIdentity { :>> providedId = "STD-IEC-60601-1-15"; }
            attribute :>> clauseNumber = "15";
            attribute :>> title = "construction of medical electrical equipment";
            attribute :>> normativeStrength = "shall";
        }
        part iec60601_1Clause16 : StandardClause {
            @MemoIdentity { :>> providedId = "STD-IEC-60601-1-16"; }
            attribute :>> clauseNumber = "16";
            attribute :>> title = "medical electrical systems";
            attribute :>> normativeStrength = "shall";
        }
        part iec60601_1Clause17 : StandardClause {
            @MemoIdentity { :>> providedId = "STD-IEC-60601-1-17"; }
            attribute :>> clauseNumber = "17";
            attribute :>> title = "electromagnetic compatibility";
            attribute :>> normativeStrength = "shall";
        }
    }



}
