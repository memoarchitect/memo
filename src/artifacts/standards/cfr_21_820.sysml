// 21 CFR Part 820 — FDA Quality System Regulation, design controls.
//
// Only §820.30 (design controls) and its paragraphs are represented: those are
// the provisions a design history file traces to. The production, purchasing
// and records subparts are QMS scope that no model element claims.
//
// Terminology: under QMSR (effective February 2026) Part 820 incorporates
// ISO 13485:2016 by reference, so a project may end up claiming both this pack
// and the 13485 one for the same document. That is two claims about one
// artifact, which is exactly what ConformsTo is for — it is not a duplicate
// registry.
package memo_artifacts_standards_cfr_21_820 {
    private import ScalarValues::*;
    private import memo_core_enumerations::*;
    private import memo_core_relationships::*;
    private import memo_artifacts_standards_traceability::*;

    private import memo_core_common::*;
    part cfr21Part820 : RegulatoryStandard {
        @MemoIdentity { :>> providedId = "STD-21-CFR-820"; }
        attribute :>> designation = "21 CFR Part 820";
        attribute :>> issuer = "FDA";
        attribute :>> appliesToRegime = (RegulatoryRegimeKind::FDA_510k, RegulatoryRegimeKind::FDA_PMA);
        part cfr820_30 : StandardClause {
            @MemoIdentity { :>> providedId = "STD-21-CFR-820-30"; }
            attribute :>> clauseNumber = "820.30";
            attribute :>> title = "design controls";
            attribute :>> normativeStrength = "shall";
            part cfr820_30a : StandardClause {
                @MemoIdentity { :>> providedId = "STD-21-CFR-820-30-A"; }
                attribute :>> clauseNumber = "820.30(a)";
                attribute :>> title = "general design control applicability";
                attribute :>> normativeStrength = "shall";
            }
            part cfr820_30b : StandardClause {
                @MemoIdentity { :>> providedId = "STD-21-CFR-820-30-B"; }
                attribute :>> clauseNumber = "820.30(b)";
                attribute :>> title = "design and development planning";
                attribute :>> normativeStrength = "shall";
            }
            part cfr820_30c : StandardClause {
                @MemoIdentity { :>> providedId = "STD-21-CFR-820-30-C"; }
                attribute :>> clauseNumber = "820.30(c)";
                attribute :>> title = "design input";
                attribute :>> normativeStrength = "shall";
            }
            part cfr820_30d : StandardClause {
                @MemoIdentity { :>> providedId = "STD-21-CFR-820-30-D"; }
                attribute :>> clauseNumber = "820.30(d)";
                attribute :>> title = "design output";
                attribute :>> normativeStrength = "shall";
            }
            part cfr820_30e : StandardClause {
                @MemoIdentity { :>> providedId = "STD-21-CFR-820-30-E"; }
                attribute :>> clauseNumber = "820.30(e)";
                attribute :>> title = "design review";
                attribute :>> normativeStrength = "shall";
            }
            part cfr820_30f : StandardClause {
                @MemoIdentity { :>> providedId = "STD-21-CFR-820-30-F"; }
                attribute :>> clauseNumber = "820.30(f)";
                attribute :>> title = "design verification";
                attribute :>> normativeStrength = "shall";
            }
            part cfr820_30g : StandardClause {
                @MemoIdentity { :>> providedId = "STD-21-CFR-820-30-G"; }
                attribute :>> clauseNumber = "820.30(g)";
                attribute :>> title = "design validation";
                attribute :>> normativeStrength = "shall";
            }
            part cfr820_30h : StandardClause {
                @MemoIdentity { :>> providedId = "STD-21-CFR-820-30-H"; }
                attribute :>> clauseNumber = "820.30(h)";
                attribute :>> title = "design transfer";
                attribute :>> normativeStrength = "shall";
            }
            part cfr820_30i : StandardClause {
                @MemoIdentity { :>> providedId = "STD-21-CFR-820-30-I"; }
                attribute :>> clauseNumber = "820.30(i)";
                attribute :>> title = "design changes";
                attribute :>> normativeStrength = "shall";
            }
            part cfr820_30j : StandardClause {
                @MemoIdentity { :>> providedId = "STD-21-CFR-820-30-J"; }
                attribute :>> clauseNumber = "820.30(j)";
                attribute :>> title = "design history file";
                attribute :>> normativeStrength = "shall";
            }
        }
    }



}
