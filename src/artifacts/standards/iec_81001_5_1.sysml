// IEC 81001-5-1:2021 — Health software and health IT systems safety, effectiveness and security — Part 5-1: Security — Activities in the product life cycle
//
// Clause instances, not type machinery. Everything here is data: adding a
// standard is one file like this one and zero TypeScript changes.
package memo_artifacts_standards_iec_81001_5_1 {
    private import ScalarValues::*;
    private import memo_core_enumerations::*;
    private import memo_core_relationships::*;
    private import memo_artifacts_standards_traceability::*;

    private import memo_core_common::*;
    part iec81001_5_1 : RegulatoryStandard {
        @MemoIdentity { :>> providedId = "STD-IEC-81001-5-1"; }
        attribute :>> designation = "IEC 81001-5-1:2021";
        attribute :>> edition = "2021";
        attribute :>> issuer = "IEC";
        attribute :>> appliesToRegime = (RegulatoryRegimeKind::CE, RegulatoryRegimeKind::MDR, RegulatoryRegimeKind::UKCA, RegulatoryRegimeKind::FDA_510k, RegulatoryRegimeKind::FDA_PMA);
        part iec81001_5_1Clause4 : StandardClause {
            @MemoIdentity { :>> providedId = "STD-IEC-81001-5-1-4"; }
            attribute :>> clauseNumber = "4";
            attribute :>> title = "general requirements";
            attribute :>> normativeStrength = "shall";
        }
        part iec81001_5_1Clause5 : StandardClause {
            @MemoIdentity { :>> providedId = "STD-IEC-81001-5-1-5"; }
            attribute :>> clauseNumber = "5";
            attribute :>> title = "software development process";
            attribute :>> normativeStrength = "shall";
            part iec81001_5_1Clause5_1 : StandardClause {
                @MemoIdentity { :>> providedId = "STD-IEC-81001-5-1-5-1"; }
                attribute :>> clauseNumber = "5.1";
                attribute :>> title = "software development planning";
                attribute :>> normativeStrength = "shall";
            }
            part iec81001_5_1Clause5_2 : StandardClause {
                @MemoIdentity { :>> providedId = "STD-IEC-81001-5-1-5-2"; }
                attribute :>> clauseNumber = "5.2";
                attribute :>> title = "software requirements analysis";
                attribute :>> normativeStrength = "shall";
            }
            part iec81001_5_1Clause5_3 : StandardClause {
                @MemoIdentity { :>> providedId = "STD-IEC-81001-5-1-5-3"; }
                attribute :>> clauseNumber = "5.3";
                attribute :>> title = "software architectural design";
                attribute :>> normativeStrength = "shall";
            }
            part iec81001_5_1Clause5_4 : StandardClause {
                @MemoIdentity { :>> providedId = "STD-IEC-81001-5-1-5-4"; }
                attribute :>> clauseNumber = "5.4";
                attribute :>> title = "software design";
                attribute :>> normativeStrength = "shall";
            }
            part iec81001_5_1Clause5_8 : StandardClause {
                @MemoIdentity { :>> providedId = "STD-IEC-81001-5-1-5-8"; }
                attribute :>> clauseNumber = "5.8";
                attribute :>> title = "software release";
                attribute :>> normativeStrength = "shall";
            }
        }
    }









}
