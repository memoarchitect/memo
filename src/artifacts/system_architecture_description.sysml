package memo_artifacts_system_architecture_description {
    private import ScalarValues::*;

            private import memo_artifacts_definitions::*;
            private import memo_core_enumerations::*;

            part def SystemArchitectureDescription specializes ArtifactKindDef {
    attribute :>> documentTitle = "System Architecture Description";
    attribute :>> regulatoryRef = "ISO/IEC/IEEE 42010:2022";
    attribute :>> artifactKind = ArtifactKind::architectureDescription;
            }
}
