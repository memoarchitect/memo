package memo_artifacts_usability_engineering_report {
    private import ScalarValues::*;

            private import memo_artifacts_definitions::*;
            private import memo_core_enumerations::*;

            part def UsabilityEngineeringReport specializes ArtifactKindDef {
    attribute :>> documentTitle = "Usability Engineering Report";
    attribute :>> regulatoryRef = "IEC 62366-1:2015";
    attribute :>> artifactKind = ArtifactKind::usabilityEngineeringReport;
            }
}
