package memo_methodology_core {
    private import ScalarValues::*;

    private import memo_core_common::*;
    private import memo_core_enumerations::*;

    part def MethodologyLibrary :> MemoPart {
        attribute version : String;
        attribute domain : String;
        attribute :>> description : String;
    }

    part def MethodologyDefinition :> MemoPart {
        attribute version : String;
        attribute domain : String;
        attribute :>> description : String;
        attribute baseMethodName : String;
    }

    part def ResolvedMethodology :> MemoPart {
        attribute version : String;
        // Risk-proportionate scope keyed to the device's software safety
        // classification (IEC 62304 A/B/C) and lifecycle stage — not a
        // "rigor dial". The class + stage determine which layers, links,
        // viewpoints, and gates a release must clear.
        attribute safetyClassification : SafetyClassKind;
        attribute lifecycleStage : LifecycleStateKind;
        attribute resolutionSummary : String;
    }

    part def ProjectMethodBinding :> MemoPart {
        attribute projectName : String;
    }

    part def DhfDocumentBinding :> MemoPart {
        attribute documentTitle : String;
        attribute groupLabel : String;
        attribute templateId : String;
        attribute viewKind : String;
        attribute regulatoryReference : String;
        attribute lifecycleStage : WorkflowStageKind;
        attribute required : Boolean;
    }

    part def Archetype :> MemoPart {
        attribute label : String;
        attribute :>> description : String;
        attribute category : String;
        attribute includedLayer : String;
        attribute includedStandard : String;
        attribute templateDir : String;
    }
}
