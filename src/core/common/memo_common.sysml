// MEMO base hierarchy. Construct-specific foundations: one base per
// SysML v2 metaclass family (part, action, port, interface, item, use case,
// requirement, constraint, verification, state, connection), each carrying
// the shared MEMO semantics. Common inheritance across metaclasses is not
// portable, so classification is shared through the metadata defs in
// memo_core_dimensions rather than through a superclass.
//
// ─── Where identity lives ───────────────────────────────────────────────
// Not in these bases. `@MemoIdentity`, below, is the one carrier: a `metadata
// def` annotates an element of ANY metaclass, so it reaches the action, port,
// item, requirement and connection families that KerML will not let inherit
// from a part def.
//
// The bases declare no `name` or `description`: every SysML element already has
// a native name, and `doc` is the native slot for prose. Display text is
// `@MemoIdentity { label }` and prose is `doc`.
//
// ─── Resources ──────────────────────────────────────────────────────────
// `MemoResource` is here, beside `MemoPart`, because the operational layer's actors
// (`User`) and workflows (`WorkflowResource`) both specialize it, and so can the
// logical layer's platform (`part def SurgicalRobot :> System, MemoResource`); core is the one
// layer all of them import. Time-driven activity-based costing needs two numbers per
// resource: what an hour of its capacity costs (staff pay, or an instrument's purchase,
// service and practical capacity) and what one use costs (a consumable). The activity
// that uses the resource supplies the time. Both are money in the project's one currency
// (memo_core_stdlib_money) and, by the principle that level 1 carries no numbers, are set
// per variant on level 2.
//
// What remains on a base is domain semantics — `status`, and whatever that
// metaclass family genuinely needs.
//
// `uuid` is the stable technical identity: never displayed, never used as a
// label, never reused. Authors normally leave it unset and let the compiler
// derive it (memo-tools assigns a v5 UUID over file+kind+id); set it
// explicitly on an element whose file or id must be free to change without
// breaking external references to it, and the authored value wins.
package memo_core_common {
    private import ScalarValues::*;

    private import memo_core_dimensions::*;
    private import memo_core_terminology::*;
    private import memo_core_enumerations::*;
    private import memo_core_stdlib_money::*;

    // The metaclass-agnostic carrier for MEMO's identity fields.
    //
    // A `metadata def` annotates an element of ANY metaclass — restriction is
    // opt-in through `annotatedElement`, and this one declares none. That is
    // what the per-metaclass base definitions below cannot do: KerML will not
    // let an action, port, item, requirement or connection inherit from a part
    // def. Metadata has no such limit, so one declaration serves them all.
    //
    // An element has five identities and they are not interchangeable:
    //
    //   1. code reference   `sfnAcquireMap`        native declaredName
    //   2. display label    "Acquire EA Map"       `label`, below
    //   3. number id        `SFN-1`                assigned, never authored
    //   4. provided id      `SPEC-4471`            `providedId`, below
    //   5. technical uuid   `e2f75cf6-…`           `uuid`, below
    //
    // 1 is native and needs no field here. 3 is generated by the compiler and
    // recorded in `memo.identity.yaml`: it is monotonic, gaps are kept, and a
    // retired number is never reused, so nothing authors it by hand.
    //
    // `label` is NOT a duplicate of the native name: the native name is a
    // lowerCamelCase identifier and must be unique in its namespace, while a
    // label is free text that legitimately repeats — measured 2026-08-18, 1278
    // labels across the ontology and examples share only 1216 distinct values,
    // because seven different ports are all correctly labelled "TLM_MODE_IN". A
    // label therefore cannot live in a name slot, native or otherwise.
    //
    // `providedId` is the identifier an EXTERNAL system knows the element by,
    // and it exists because that system's scheme is not MEMO's: a customer
    // numbering software requirements `SPEC-4471` cannot be made to use `SWR-`,
    // and overwriting the generated number to please them would break the
    // guarantee that numbers are never reassigned.
    //
    // `uuid` is machine identity. Authored values win over the registry, which
    // wins over derivation — so an element whose file must move can pin its own
    // uuid.
    //
    // Deliberately absent: `name` and `description` (native name and `doc`),
    // `rationale` (standard `@Rationale`), and `id` (the generated number id
    // and `providedId`).
    metadata def MemoIdentity {
        attribute label : String[0..1];
        attribute providedId : String[0..1];
        attribute uuid : String[0..1];
        attribute shortDescription : String[0..1];
        attribute sourceReference : String[0..1];
    }

    // Marks a definition as a KIND — an extension of the ontology — rather than a model element.
    // A project definition that specializes an ontology kind is, structurally, either a new kind
    // (`ProjectStakeholder`) or one particular thing (`InfusionPumpSystem`); nothing in the
    // SysML tells the two apart, so the author says which. A marked definition, and what is typed
    // by it, takes `idPrefix` as the family of its display ids (`<idPrefix>-1`). Anything unmarked
    // takes the family of the ontology kind it descends from.
    metadata def MemoKind {
        attribute idPrefix : String;
    }

    // ─── Single abstract part root ──────────────────────────────────
    // Every structural MEMO concept specializes MemoPart. Identity and
    // traceability are attributes of this one root — MEMO has no separate
    // IdentifiedElement/TraceableElement classes, because *everything* is
    // identifiable and traceable by definition; that is not a type a modeler
    // picks. MemoPart is abstract: never instantiated, only specialized.
    //
    // Axis ownership (horizontal architecture layer vs. vertical assurance
    // discipline) is NOT an attribute — it is the element's owning package
    // (memo_architecture_* xor memo_assurance_*), enforced by CR-ONT-045. The
    // remaining dimensions are orthogonal to the axis: realization stage,
    // cross-cutting concern, and editorial status. Deliberately NOT declared
    // here: `name` and `description`. A name slot on a MEMO base is a second
    // spelling of the native name every SysML element already has, and a
    // description slot is a second spelling of `doc`. The display label — free
    // text, legitimately repeating — lives on `@MemoIdentity { label }`, which
    // annotates any metaclass and so reaches the behaviours and views that
    // cannot specialize a part. The long prose lives in `doc`.
    // `shortDescription` on `@MemoIdentity` remains the one-line register a
    // table cell or chip shows whole; it is a different density, not a
    // different authority.
    abstract part def MemoPart {
        @MemoIdentity { :>> label = "Part"; }
        // editorial status and lifecycle
        attribute status : ElementStatusKind;
        attribute lifecycleState : LifecycleStateKind;
        // orthogonal dimensions
        attribute realizationStage : RealizationStageKind[0..1];
        attribute crossCuttingConcerns : CrossCuttingConcernKind[0..*];
        attribute concerns : ConcernKind[0..*];
        attribute applicableStandards : ExternalReference[0..*];
        attribute codes : TerminologyCode[0..*];
        // The part's identity in the product structure, assigned by the user, not by MEMO. A revision is
        // alphabetic: A, B, … Z, AA.
        attribute partNumber : String[0..1];
        attribute revision : String[0..1];
    }

    // A resource a body of work spends: an instrument, a person, a consumable or the platform. It
    // carries what an hour of its capacity costs and what one use of it costs.
    abstract part def MemoResource specializes MemoPart {
        @MemoIdentity { :>> label = "Resource"; }
        attribute capacityCostRate : CostRateValue[0..1];
        attribute unitCost : MoneyValue[0..1];
    }

    // ─── Role bases retained from the original kernel, re-founded on
    //     MemoPart so all existing content inherits the dimensions. ───
    part def RequirementDriver specializes MemoPart {
        @MemoIdentity { :>> label = "Requirement driver"; }
    }
    abstract part def VerifiableElement specializes MemoPart {
        @MemoIdentity { :>> label = "Verifiable element"; }
    }
    part def InterfaceElement specializes MemoPart {
        @MemoIdentity { :>> label = "Interface element"; }
    }
    enum def EvidenceKind { enum testArtifact; enum evidence; enum formativeEvaluation; enum usabilityValidation; enum securityClaim; }
    part def MemoEvidence specializes MemoPart {
        @MemoIdentity { :>> label = "Evidence"; }
        attribute evidenceKind : EvidenceKind;
        attribute version : String;
        attribute artifactKind : ArtifactKind[0..1];
        attribute resultSummary : String;
        attribute evidenceType : String;
        attribute integrityStatus : String;
        // What an IEC 62366-1 evaluation record reports. These are on the
        // standard's terms, not on in-tree usage: MEMO is a library, so what
        // its own examples happen to set says nothing about what an adopter's
        // usability file needs.
        attribute participantProfile : String;
        attribute participantCount : Integer;
        attribute acceptanceCriteria : String;
        attribute evaluationMethod : String;
        attribute findingsSummary : String;
        attribute designChangesTriggered : String;
    }
    abstract part def AnalysisArtifact specializes MemoPart {
        @MemoIdentity { :>> label = "Analysis artifact"; }
    }

    // ─── Construct-specific foundations (non-part metaclasses) ───────

    // Behavioral foundation: operational activities, tasks, system actions,
    // and interaction steps specialize MemoAction.
    action def MemoAction {
        @MemoIdentity { :>> label = "Action"; }
        attribute status : ElementStatusKind;
    }

    // An occurrence whose start is guarded by a precondition and whose end by a postcondition: it
    // starts only once the precondition holds and is done only once the postcondition does. The
    // two are native `constraint` features a usage redefines with its own expression:
    //
    //     action fnDose : SystemFunction {
    //         in rate : Real;
    //         constraint :>> precondition { rate >= 0 }
    //     }
    //
    // The shape is the SYSMOD method's `ConstrainedOccurrence`. It is declared on an `occurrence def`
    // because `startShot` and `endShot` are found through one; `MemoFunction` specializes it.
    abstract occurrence def MemoConstrainedOccurrence {
        @MemoIdentity { :>> label = "Constrained occurrence"; }
        constraint precondition;
        constraint postcondition;
        ref occurrence :>> startShot { assert constraint :> precondition; }
        ref occurrence :>> endShot { assert constraint :> postcondition; }
    }

    // Boundary feature foundation for typed ports.
    port def MemoPort {
        @MemoIdentity { :>> label = "Port"; }
        attribute status : ElementStatusKind;
    }

    // Interaction-contract foundation for interface definitions between ports.
    abstract interface def MemoInterface {
        @MemoIdentity { :>> label = "MEMO interface"; }
        end source;
        end target;
    }

    // Single item foundation. Standards, hazards, stored software data, and
    // message payloads are all item-native concepts. Whether an item is
    // exchanged is expressed by its use in a port or flow, not by a second
    // ontology root.
    abstract item def MemoItem {
        @MemoIdentity { :>> label = "Item"; }
        attribute status : ElementStatusKind;
        // What the item CARRIES, as distinct from what it is called. Removed
        // by `595bfac` while modelling native wrappers; nothing replaced them,
        // and every exchange item in the examples went on setting them. A
        // measured value without its unit, its range, or its terminology code
        // is not a regulated data item — an IVD result is "5.5 mg/dL, LOINC
        // 2345-7", not "5.5".
        attribute semantics : String;
        // A range is not a field here: it is a constraint on the type of the attribute holding the value.
        attribute unit : String;
        attribute encoding : String;
        attribute timestampRequired : Boolean;
        attribute codes : TerminologyCode[0..*];
    }

    // Use-case foundation. The domain UseCase adds its goal and actor
    // references; identity is `@MemoIdentity`, as everywhere else.
    abstract use case def MemoUseCase {
        @MemoIdentity { :>> label = "MEMO use case"; }
        attribute status : ElementStatusKind;
    }

    // General constraint foundation. Executable consistency rules and
    // reusable quantitative constraints are both native constraint defs.
    abstract constraint def MemoConstraint {
        attribute status : ElementStatusKind;
    }

    // Requirement-family foundations. MemoNeed captures a problem-space
    // expectation in stakeholder language; MemoRequirement a testable
    // solution-space obligation. Shared base of the requirement family. It
    // exists so a relation end can say "a need or a requirement" with one type
    // name. The text of a need or a requirement is its native `doc`, which SysML
    // defines as the requirement's text.
    abstract requirement def MemoRequirementElement {
        @MemoIdentity { :>> label = "Requirement element"; }
        attribute status : ElementStatusKind;
    }

    requirement def MemoNeed :> MemoRequirementElement {
        @MemoIdentity { :>> label = "MEMO need"; }
        attribute needSource : String;
        attribute priority : String;
    }

    requirement def MemoRequirement :> MemoRequirementElement {
        @MemoIdentity { :>> label = "MEMO requirement"; }
        attribute acceptanceCriteria : String;
    }

    // Top-level goal a system or operation exists to fulfil, with its success
    // criteria and context. Domain layers specialize it; the medical-device
    // intended use (memo_architecture_operational_structure::IntendedUse) is a
    // MemoMission. It is a `requirement def` because a mission is the top
    // obligation everything below it derives from, not a structural thing. The
    // prose a document renders is `doc`, and the one-line register a table cell
    // shows is `@MemoIdentity`'s `shortDescription`.
    abstract requirement def MemoMission :> MemoRequirementElement {
        @MemoIdentity { :>> label = "Mission"; }
        attribute missionKind : String;
        attribute successCriteria : String;
        attribute operationalContext : String;
    }

    // Verification-case foundation. A SysML v2 verification case is a behaviour
    // (it checks requirements), and KerML forbids a behaviour from specializing
    // the part-based MemoPart — so, like MemoAction, it stands on its own and
    // takes its identity from `@MemoIdentity`.
    verification def MemoVerificationCase {
        @MemoIdentity { :>> label = "MEMO verification case"; }
        attribute status : ElementStatusKind;
    }

    // State foundation. SysML v2 states (state machines and their mode states)
    // are behaviours, so — like MemoAction and MemoVerificationCase — they
    // cannot specialize MemoPart and are annotated instead.
    // Transitions stay part-based to keep their traceable safety
    // attributes (id, sourceReference, priority, sameStepCritical).
    enum def StateKind { enum mode; enum logical; }

    state def MemoState {
        @MemoIdentity { :>> label = "State"; }
        attribute stateKind : StateKind;
        attribute status : ElementStatusKind;
        attribute modeKind : String;
        attribute entryCondition : String;
        attribute exitCondition : String;
        attribute modePurpose : String;
    }

    part def Citation specializes MemoPart {
        @MemoIdentity { :>> label = "Citation"; }
        attribute source : String;
        attribute section : String;
        attribute uri : String;
        attribute year : String;
    }
}
