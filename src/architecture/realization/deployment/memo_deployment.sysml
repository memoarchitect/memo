// Deployment (allocation) view: SoftwareModule buildsInto SoftwareDeploymentUnit;
// SoftwareDeploymentUnit deploysTo ProcessingNode. Software deploys only to capable
// execution nodes (rules/crosslayer).
//
// `HostedBy` is NOT part of that chain. It is `processingNode : ProcessingNode
// -> hostAssembly : PhysicalAssembly`: physical hosting of a node by the
// assembly it is mounted in, running the other way and between different
// things. Software reaches a node through DeploysTo.
package memo_architecture_realization_deployment {
    private import memo_core_stdlib_quantities::*;
    private import Metaobjects::SemanticMetadata;
    private import ScalarValues::*;
    // The standard's allocation base, which the two AADL bindings below root
    // on alongside MemoRelationship.
    private import Allocations::Allocation;

    private import memo_core_common::*;
    private import memo_core_enumerations::*;
    private import memo_core_relationships::*;
    private import memo_architecture_implementation_software_structure::*;
    private import memo_architecture_implementation_software_runtime::*;
    private import memo_architecture_implementation_hardware_common::PhysicalComponent;
    private import memo_architecture_realization_physical::*;
    private import memo_architecture_functional_functions::*;
    private import memo_architecture_logical_structure::*;
    private import memo_architecture_logical_interfaces::*;                   // ComponentExchange

    part def SoftwareDeploymentUnit specializes MemoPart {
        @MemoIdentity { :>> label = "Software deployment unit"; }
        attribute unitKind : String;
        attribute version : String;
        attribute integrityProtection : String;
        attribute installationMechanism : String;
    }

    part def RuntimeEnvironment specializes MemoPart {
        @MemoIdentity { :>> label = "Runtime environment"; }
        attribute environmentKind : String;
        attribute osOrRtos : String;
        attribute providedServices : String;
        attribute certificationEvidence : String;
    }

    // A module BUILDS INTO a deployment unit: that is an allocation, and the
    // language has one. Rooted like MemoryBinding / ConnectionBinding below,
    // so the whole deployment family spells allocation the same way.
    allocation def BuildsInto :> MemoRelationship, Allocations::Allocation {
        @MemoIdentity { :>> label = "Builds into"; }
        end module : SoftwareModule :>> source;
        end deploymentUnit : SoftwareDeploymentUnit :>> target;
    }
    abstract connection buildsIntoLinks : BuildsInto[*];
    metadata def <buildsInto> BuildsIntoMetadata :> SemanticMetadata {
        :> annotatedElement : SysML::AllocationDefinition;
        :> annotatedElement : SysML::AllocationUsage;
        :>> baseType = buildsIntoLinks meta SysML::Usage;
    }
    // A logical component is REALIZED BY the hardware or software that implements it. The
    // logical and the implementation architectures are separate structures and stay
    // separate: nothing is nested (a logical component never contains software or a
    // physical part, CR-ONT-078); the two are joined by an allocation, as the language
    // joins structures across domains (SysML-textual-bnf.kebnf:792-801, AllocationDefinition and AllocationUsage) and as SYSMOD
    // does with its `logical2product` allocation, logical architecture to product
    // architecture, logical as the source. The target is any part, as HostedBy's ends are:
    // a hardware assembly and a software system are both MemoParts.
    allocation def RealizedBy :> MemoRelationship, Allocations::Allocation {
        @MemoIdentity { :>> label = "Realized by"; }
        end logicalComponent : LogicalComponent :>> source;
        end realization : MemoPart :>> target;
    }
    abstract connection realizedByLinks : RealizedBy[*];
    metadata def <realizedBy> RealizedByMetadata :> SemanticMetadata {
        :> annotatedElement : SysML::AllocationDefinition;
        :> annotatedElement : SysML::AllocationUsage;
        :>> baseType = realizedByLinks meta SysML::Usage;
    }
    // Written `allocation x : DeploysTo allocate a to b;`.
    allocation def DeploysTo :> MemoRelationship, Allocations::Allocation {
        @MemoIdentity { :>> label = "Deploys to"; }
        attribute deploymentKind : DeploymentKind;
        end deploymentUnit : SoftwareDeploymentUnit :>> source;
        end node : ProcessingNode :>> target;
    }
    abstract connection deploysToLinks : DeploysTo[*];
    metadata def <deploysTo> DeploysToMetadata :> SemanticMetadata {
        :> annotatedElement : SysML::AllocationDefinition;
        :> annotatedElement : SysML::AllocationUsage;
        :>> baseType = deploysToLinks meta SysML::Usage;
    }
    connection def ProvidesEnvironment :> MemoRelationship {
        @MemoIdentity { :>> label = "Provides environment"; }
        end node : ProcessingNode :>> source;
        end environment : RuntimeEnvironment :>> target;
    }
    abstract connection providesEnvironmentLinks : ProvidesEnvironment[*];
    metadata def <providesEnvironment> ProvidesEnvironmentMetadata :> SemanticMetadata {
        :> annotatedElement : SysML::ConnectionDefinition;
        :> annotatedElement : SysML::ConnectionUsage;
        :>> baseType = providesEnvironmentLinks meta SysML::Usage;
    }

    // ─── AADL bindings (SAE AS5506) ────────────────────────────
    //
    // AADL's analytic power is that EVERYTHING is bound to something, and the
    // binding is where latency, bandwidth and fault propagation accrue.
    // `DeploysTo` is `actual_processor_binding`. Without the other two,
    // `SoftwareComponent.memoryBudget` is unanalysable and
    // `EndToEndFlow.latencyBudgetMs` cannot be checked against the media the
    // flow traverses.
    //
    // Both are `allocation def`s rooted on the standard's
    // `Allocations::Allocation`, because a binding IS an allocation and the
    // language says so. The double specialization keeps MEMO's identification
    // core from `MemoRelationship` while adding the standard's allocation
    // semantics; both root on `Connections::BinaryConnection`, so this is a
    // diamond and not a conflict.

    // AADL `actual_memory_binding`. Which memory a software component's code
    // and data occupy — what makes a memory budget a claim about a device
    // rather than a string.
    allocation def MemoryBinding :> MemoRelationship, Allocations::Allocation {
        @MemoIdentity { :>> label = "Memory binding"; }
        attribute bindingKind : String;
        end boundComponent : SoftwareComponent :>> source;
        end memory : MemoryDevice :>> target;
    }
    abstract connection memoryBindingLinks : MemoryBinding[*];
    metadata def <memoryBinding> MemoryBindingMetadata :> SemanticMetadata {
        :> annotatedElement : SysML::AllocationDefinition;
        :> annotatedElement : SysML::AllocationUsage;
        :>> baseType = memoryBindingLinks meta SysML::Usage;
    }

    // AADL `actual_connection_binding`. Which physical thing carries an
    // interface: a network medium under a component exchange, a cable or
    // harness under a hardware `Interface`, a connector, a tube. The source is
    // the interface usage rather than a link, because the interface is the
    // ELEMENT that owns the budget and a link instance is not something the
    // graph can bind to; it is also exactly where the latency the medium
    // contributes has to be accounted. Ends are the two bases (MemoInterface,
    // PhysicalComponent) so one binding serves every layer.
    allocation def ConnectionBinding :> MemoRelationship, Allocations::Allocation {
        @MemoIdentity { :>> label = "Connection binding"; }
        attribute allocatedBandwidth : String;
        attribute mediumLatencyMs : DurationValue;
        end boundExchange : MemoInterface :>> source;
        end medium : PhysicalComponent :>> target;
    }
    abstract connection connectionBindingLinks : ConnectionBinding[*];
    metadata def <connectionBinding> ConnectionBindingMetadata :> SemanticMetadata {
        :> annotatedElement : SysML::AllocationDefinition;
        :> annotatedElement : SysML::AllocationUsage;
        :>> baseType = connectionBindingLinks meta SysML::Usage;
    }

    // ─── AADL-style flow modeling (SAE AS5506) ───────────────────────────
    // AADL separates a flow *specification* (declared at a component boundary
    // as source / sink / path through ports) from a flow *implementation*
    // (its routing through subcomponents and connectors), and traces a
    // complete source→sink flow as an *end-to-end flow* across the assembly.
    // MEMO keeps software and hardware as distinct families (SoftwareModule
    // vs ProcessingNode) and analyses the flow across their binding — the same
    // way AADL end-to-end flows account for processor/bus bindings — enabling
    // latency and fault-propagation analysis.
    enum def FlowSpecKind {
        enum source;
        enum sink;
        enum path;
    }
    // A flow declared at a logical component boundary (in-port → out-port).
    part def FlowSpecification specializes MemoPart {
        @MemoIdentity { :>> label = "Flow specification"; }
        attribute flowKind : FlowSpecKind;
        ref inPort : LogicalPort[0..1];
        ref outPort : LogicalPort[0..1];
    }
    // A complete source→sink flow traced across the layers and the software→
    // hardware binding it traverses. `latencyBudgetMs` and `analysisPurpose`
    // (latency | fault-propagation | security) drive the AADL-style analysis.
    part def EndToEndFlow specializes MemoPart {
        @MemoIdentity { :>> label = "End to end flow"; }
        attribute latencyBudgetMs : DurationValue;
        attribute analysisPurpose : String;
        ref sourceFunction : MemoFunction[0..1];
        ref sinkFunction : MemoFunction[0..1];
        ref logicalSegments : LogicalComponent[0..*];
        // Runtime C&C components (SEI) — the elements actually bound to hardware.
        ref softwareSegments : SoftwareComponent[0..*];
        ref hostNodes : ProcessingNode[0..*];
    }
    // The end-to-end flow is realized by an ordered flow specification, one
    // segment per traversed component boundary (AADL flow-spec → end-to-end).
    connection def FlowComprisesSpec :> MemoRelationship {
        @MemoIdentity { :>> label = "Flow comprises spec"; }
        attribute segmentOrder : Integer;
        end endToEndFlow : EndToEndFlow :>> source;
        end spec : FlowSpecification :>> target;
    }
    abstract connection flowComprisesSpecLinks : FlowComprisesSpec[*];
    metadata def <flowComprisesSpec> FlowComprisesSpecMetadata :> SemanticMetadata {
        :> annotatedElement : SysML::ConnectionDefinition;
        :> annotatedElement : SysML::ConnectionUsage;
        :>> baseType = flowComprisesSpecLinks meta SysML::Usage;
    }
    // The flow traverses a software→hardware binding; latency accrues here.
    // A binding IS an allocation, exactly as MemoryBinding and
    // ConnectionBinding already declare.
    allocation def FlowTraversesBinding :> MemoRelationship, Allocations::Allocation {
        @MemoIdentity { :>> label = "Flow traverses binding"; }
        end endToEndFlow : EndToEndFlow :>> source;
        end deploymentUnit : SoftwareDeploymentUnit :>> target;
    }
    abstract connection flowTraversesBindingLinks : FlowTraversesBinding[*];
    metadata def <flowTraversesBinding> FlowTraversesBindingMetadata :> SemanticMetadata {
        :> annotatedElement : SysML::AllocationDefinition;
        :> annotatedElement : SysML::AllocationUsage;
        :>> baseType = flowTraversesBindingLinks meta SysML::Usage;
    }
}
