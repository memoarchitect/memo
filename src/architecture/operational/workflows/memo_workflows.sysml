// First-class operational workflows. A use case is the user's goal; an
// OperationalWorkflow is the ANALYSIS of one body of work that pursues it: who
// does it, where, with what equipment, between which entry and completion
// conditions, and (from the needs that point at it) what is needed and what
// is not yet met. It may exist before any device is selected. It is not a
// sequence of steps: the steps are its scenarios' (memo_architecture_operational_scenarios),
// each one stepwise path with pre- and post-conditions, and an occurrence is
// one execution of a scenario.
//
// IEC 62366-1 is the guide: the workflow is the use specification (5.1) scoped
// to one body of work, with the UI characteristics related to safety (5.2) and
// the known use-related hazards (5.3) its analysis draws on; a scenario is the
// standard's use scenario, a sequence of tasks by a user in a use environment.
// The standard has no "workflow"; this is MEMO's.
//
// So a workflow is a part, not an action: an action's nested actions are all
// performed, and a workflow's scenarios are alternatives. It owns its scenarios
// as nested actions, the way a part owns what it can do.
//
// A workflow's equipment is `WorkflowResource` parts, each a `MemoResource` with its cost rate.
// A generic resource is specialized by the product that fills it (`part def ProductXStapler :>
// Stapler`), which is why there is no `resolvedProduct` reference: native specialization says it.
package memo_architecture_operational_workflows {
    private import Metaobjects::SemanticMetadata;
    private import ScalarValues::*;

    private import memo_core_stdlib_quantities::*;
    private import memo_core_stdlib_money::*;

    private import memo_core_common::*;
    private import memo_core_enumerations::*;
    private import memo_core_relationships::*;
    private import memo_architecture_operational_context_actors::*;
    private import memo_architecture_operational_context_use_context::*;
    private import memo_architecture_operational_activities::*;
    private import memo_architecture_operational_use_cases::*;

    abstract part def OperationalWorkflow specializes MemoPart {
        @MemoIdentity { :>> label = "Operational workflow"; }
        // Where the body of work starts and ends. A scenario's pre- and
        // post-conditions are its own path's, inside these.
        attribute entryCondition : String;
        attribute completionCondition : String;
        // What one procedure costs apart from its activities (set-up, capital per case); a number,
        // so it is set on a level-2 variant's workflow, never on level 1.
        attribute perProcedureCost : MoneyValue[0..1];
        // The context and environment of use (IEC 62366-1 5.1), as modelled
        // elements rather than a sentence: the care setting, jurisdiction and
        // connected use are UseContext's, lighting and noise UseEnvironment's.
        ref useContext : UseContext[0..1];
        ref useEnvironment : UseEnvironment[0..1];
        // The equipment and other resources the work needs are the workflow's
        // own `WorkflowResource` parts. Users are not listed: they are who
        // `perform`s its scenarios' steps. Needs point here (Need.workflow);
        // the workflow does not list them, because assurance may depend on
        // architecture and not the reverse.
    }

    // A workflow is at the level of the use case it realizes, and says so by its type: a
    // `ClinicalWorkflow` realizes a `ClinicalUseCase` (no product, no number); a `SystemWorkflow`
    // realizes a `SystemUseCase` (one variant, every number). CR-ONT-103 keeps the two in step.
    part def ClinicalWorkflow specializes OperationalWorkflow {
        @MemoIdentity { :>> label = "Clinical workflow"; }
    }
    part def SystemWorkflow specializes OperationalWorkflow {
        @MemoIdentity { :>> label = "System workflow"; }
    }

    // The use case a workflow realizes. Many workflows may trace to one use
    // case; the use case does not own its workflows (the trace points upward,
    // workflow → use case).
    connection def RealizesUseCase :> MemoRelationship {
        @MemoIdentity { :>> label = "Realizes use case"; }
        end realizingWorkflow : OperationalWorkflow :>> source;
        end realizedUseCase : UseCase :>> target;
    }
    abstract connection realizesUseCaseLinks : RealizesUseCase[*];
    metadata def <realizesUseCase> RealizesUseCaseMetadata :> SemanticMetadata {
        :> annotatedElement : SysML::ConnectionDefinition;
        :> annotatedElement : SysML::ConnectionUsage;
        :>> baseType = realizesUseCaseLinks meta SysML::Usage;
    }


    enum def ResourceKind {
        enum instrument;
        enum equipment;
        enum consumable;
        enum material;
        enum information;
        enum space;
    }

    // Resources a workflow requires: instruments, equipment, consumables, materials, information
    // or space, by reference. Owned by the workflow as its parts. A staff member is not one: that
    // is a `User`, which is a `MemoResource` of its own.
    part def WorkflowResource specializes MemoResource {
        @MemoIdentity { :>> label = "Workflow resource"; }
        attribute resourceKind : ResourceKind;
        attribute quantity : Natural;
        attribute reprocessingDuration : DurationValue[0..1];
    }

    // ── Workflow-level relationships ─────────────────────────────
    // An element supports (affords, enables) an action — e.g. a UI element that
    // affords a user task. Use-case and capability tracing are direct refs
    // (OperationalWorkflow.useCase, OperativeAction.contributesToCapabilities),
    // so this is one plain relation.

}
