package memo_architecture_operational_structure {
    private import Metaobjects::SemanticMetadata;
    private import ScalarValues::*;

    private import memo_core_common::*;
    private import memo_core_enumerations::*;
    private import memo_core_relationships::*;
    private import memo_architecture_operational_use_cases::*;

    // IEC 62366-1 / ISO 14971 intended use: the medical device's declared
    // purpose and the root of the operational spine. A MemoMission, because
    // "mission" has no medical-device meaning — intended use is what a device
    // exists to do. It is a `requirement def`: the intended use is the top
    // obligation the device's design inputs derive from, and ISO 14971 5.2 asks
    // for it to be documented as the starting point of risk analysis.
    requirement def IntendedUse :> MemoMission {
        @MemoIdentity { :>> label = "Intended use"; }
        attribute indication : String;
        attribute contraindication : String;
        attribute patientPopulation : String;
        attribute clinicalBenefit : String;
        attribute regulatoryClassification : String;
    }
    part def OperationalEntity specializes MemoPart {
        @MemoIdentity { :>> label = "Operational entity"; }
        attribute entityKind : OperationalEntityKind;
        attribute operationalDomain : String;
        attribute responsibility : String;
    }
    part def OperationalCapability specializes MemoPart {
        @MemoIdentity { :>> label = "Operational capability"; }
        attribute capabilityLevel : String;
        attribute preCondition : String;
        attribute postCondition : String;
    }

    // The intended use requires these operational capabilities (ARCADIA:
    // Mission Requires Capability).
    connection def RequiresCapability :> MemoRelationship {
        @MemoIdentity { :>> label = "Requires capability"; }
        end requiringIntendedUse : IntendedUse :>> source;
        end requiredCapability : OperationalCapability :>> target;
    }
    abstract connection requiresCapabilityLinks : RequiresCapability[*];
    metadata def <requiresCapability> RequiresCapabilityMetadata :> SemanticMetadata {
        :> annotatedElement : SysML::ConnectionDefinition;
        :> annotatedElement : SysML::ConnectionUsage;
        :>> baseType = requiresCapabilityLinks meta SysML::Usage;
    }

    // An operational capability enables a use case (the ability the actor draws
    // on to accomplish the goal). Capability is tied to the use case, not to
    // individual activities.
    connection def EnablesUseCase :> MemoRelationship {
        @MemoIdentity { :>> label = "Enables use case"; }
        end enablingCapability : OperationalCapability :>> source;
        end enabledUseCase : UseCase :>> target;
    }
    abstract connection enablesUseCaseLinks : EnablesUseCase[*];
    metadata def <enablesUseCase> EnablesUseCaseMetadata :> SemanticMetadata {
        :> annotatedElement : SysML::ConnectionDefinition;
        :> annotatedElement : SysML::ConnectionUsage;
        :>> baseType = enablesUseCaseLinks meta SysML::Usage;
    }

}
