// User interface and interaction. A small semantic hierarchy: concrete widget
// forms (button, knob, chart …) are enum classifications, not classes. UI state
// is distinct from system state (memo_architecture_functional_behavior) and
// from device modes (memo_architecture_logical_structure::LogicalMode). UI is
// an implementation concern (rendered UI is software; physical controls are
// hardware), so it lives in the implementation layer, not operational.
package memo_architecture_implementation_ui {
    private import Metaobjects::SemanticMetadata;
    private import ScalarValues::*;

    private import memo_core_common::*;
    private import memo_core_enumerations::*;
    private import memo_assurance_safety_risk::*;   // RiskControlMeasure
    private import memo_core_relationships::*;
    private import memo_architecture_operational_activities::*;
    private import memo_architecture_operational_scenarios::*;
    private import memo_architecture_operational_use_cases::*;
    private import memo_architecture_functional_functions::*;
    private import memo_architecture_implementation_software_structure::*;
    private import memo_architecture_implementation_hardware_common::*;
    private import memo_assurance_human_factors::*;

    // Every concrete UI form, holding and held alike. A screen is not a
    // different KIND of thing from a button — it is a UIElement that happens to
    // contain others, exactly as an assembly is a part that contains parts.
    // The forms below are classifications, not classes, so one tree carries the
    // whole interface.
    enum def UIElementFormKind {
        // ── forms that hold other elements ──
        enum screen;
        enum dialog;
        enum panel;
        enum menu;
        enum tab;
        enum drawer;
        enum wizardStep;
        // ── controls the user acts on ──
        // Rendered controls only. A knob, toggle, lamp, or buzzer the user
        // touches is not software: it is an OperatorInterfaceElement below.
        enum button;
        enum field;
        enum selector;
        enum slider;
        // ── forms that present information ──
        enum table;
        enum chart;
        enum icon;
        enum textMessage;
        // ── chrome ──
        // Non-functional: a rule, a background, a brand mark. Declared, never
        // merely implied — CR-MED-110 exempts `decoration` from needing a
        // design record, so an element left unclassified fails rather than
        // slipping through as scenery.
        enum decoration;
    }

    // ─── Screen geometry ─────────────────────────────────────────
    // Position and size of a UIElement inside its PARENT element, each value
    // normalized to 0..1 of the parent's box — not pixels. Two consequences
    // are wanted: an element survives a re-capture at a different resolution
    // or device scale, and a child's box is stated against its parent, which
    // is exactly what the containment tree already asserts. Absolute pixels
    // stay recoverable from the ScreenCapture's pixelWidth / pixelHeight.
    attribute def RegionBounds {
        attribute x : Real;
        attribute y : Real;
        attribute width : Real;
        attribute height : Real;
    }

    // How an element appears relative to its parent and siblings. It records
    // design intent a bare rectangle cannot: an element whose box escapes its
    // parent and covers its siblings is a defect if it is `inline` and correct
    // if it is `overlay`, and the geometry alone does not say which. A
    // renderer reads it to decide what to clip and what to draw on top; a
    // reviewer reads it to know whether an overlap is intended.
    enum def UIDisclosureKind {
        enum inline;       // laid out inside the parent, sharing space with siblings
        enum overlay;      // dropdown, popover, modal — drawn OVER parent and siblings
        enum transient;    // tooltip, toast — appears over everything, then withdraws
        enum scrolled;     // inside the parent, but beyond its viewport until scrolled
        enum conditional;  // rendered only while a stated condition holds
    }

    // How the element's bounds were obtained. Automatic boundary detection
    // PROPOSES; a reviewer DISPOSES. In a regulated review the reader must be
    // able to see which boxes a human confirmed and which the tool guessed, so
    // that provenance is model content and not a workbench-only flag.
    enum def BoundsDetectionKind {
        enum manual;
        enum automatic;
        enum automaticConfirmed;
        enum imported;
    }

    // The interaction intents a step or action can carry.
    enum def InteractionIntentKind {
        enum userInput;
        enum feedback;
        enum navigation;
        enum confirmation;
        enum inputValidation;
        enum errorMessage;
        enum alarmAnnunciation;
        enum acknowledgement;
        enum cancellation;
        enum timeout;
        enum lockout;
        enum correction;
        enum recovery;
    }

    part def UserInterface specializes MemoPart {
        @MemoIdentity { :>> label = "User interface"; }
        attribute modality : String;
        attribute uiTechnology : String;
    }

    // `ErrorAtElement` and `ElementTriggersAction` take `MemoPart`: IEC 62366-1
    // puts the whole means of interaction in scope, and a mis-keyed connector,
    // a moulded marking on a housing, a tube routed backwards are use errors at
    // parts that are not interface elements.

    // One UIElement — the single UI part type. The widget form — holding
    // (screen/panel/dialog), acting (button/knob/slider), presenting
    // (field/table/chart), physical (knob/switch/indicatorLamp/haptic), or
    // decorative — is the `formKind` enum, not a subclass.
    // Input/output/navigation/alarm/display/physical-control descriptors are
    // optional attributes; a physical control's mechanical realization is a
    // hardware part linked by ControlImplementedBy.
    //
    // Composition is the ordinary `Composes` relation, so a screen's element
    // tree is an ordinary part tree: CR-ONT-001 already forbids cycles in it,
    // impact analysis already walks it, and requirements, functions, use
    // errors, and risk controls already trace to it. Screen layout adds four
    // numbers to that tree — it does not add a tree.
    //
    // A UIElement IS a structural SOFTWARE ITEM (IEC 62304 §3.25) and
    // specializes SoftwareElement, inheriting safetyClass and complexity, so the
    // interface is classified and decomposed like the software it is.
    //
    // It specializes SoftwareElement and NOT SoftwareModule: the module view is
    // CODE, and a screen is not a source module. Runtime processes are
    // SoftwareComponent, code is SoftwareModule, and the UI is a third view of
    // the same software — a sibling of those, not a kind of either.
    part def UIElement specializes SoftwareElement {
        @MemoIdentity { :>> label = "UI element"; }
        attribute formKind : UIElementFormKind;
        // The visible label. Held here rather than on a shared interaction
        // base: a physical control's label is moulded or printed, and is
        // `legendText` on OperatorInterfaceElement.
        attribute labelText : String;
        // ── alarm annunciation (optional; IEC 60601-1-8) ──
        // On the rendered element, because that is where every modelled
        // annunciation lives. A physical annunciator that needs a priority
        // wants an alarm concept of its own, not three attributes copied onto
        // every front-panel part.
        attribute alarmPriority : NotificationPriorityKind[0..1];
        attribute annunciationModality : String;
        attribute silenceable : Boolean;
        // ── screen layout (optional; set for elements that are laid out) ──
        // Bounds are relative to the parent element in the Composes tree; a
        // root screen's bounds are the full frame.
        attribute bounds : RegionBounds[0..1];
        attribute disclosureKind : UIDisclosureKind[0..1];
        // The condition under which the element renders; meaningful when
        // disclosureKind is `conditional`.
        attribute visibilityCondition : String;
        // Boundary colour as a CSS colour token. Presentation, but modelled: a
        // review print, an exported figure, and the workbench must agree on
        // which box is which, and a colour assigned only in a tool session does
        // not survive the export.
        attribute boundaryColor : String;
        // Capture-relative fill transparency for region review overlays. A
        // modelled value keeps interactive review and exported figures aligned.
        attribute boundaryOpacity : Real[0..1];
        // Stroke width of the same box, in pixels. Colour and opacity are
        // modelled so a review print, an exported figure, and the workbench
        // agree on which box is which; a width chosen per renderer breaks that
        // agreement for exactly the same reason.
        attribute boundaryWidth : Real[0..1];
        attribute detectionMethod : BoundsDetectionKind[0..1];
        attribute detectionConfidence : Real[0..1];
        attribute confirmedBy : String;
        attribute confirmedAt : String;
        // ── role of a holding form (optional) ──
        attribute navigationRole : String;
        // input descriptors (optional)
        attribute inputConstraints : String;
        attribute defaultValue : String;
        // output / display descriptors (optional)
        attribute updateRate : String;
        attribute unitsDisplayed : String;
        attribute informationContent : String;
    }

    // ─── Physical operator interface ─────────────────────────────
    // The hardware the user actually touches and reads. IEC 60601-1 marks
    // "controls and instruments" and defines OPERATOR; this is that surface,
    // covering both directions — what the operator actuates and what the
    // device shows back — because a front panel is one interface, not two.
    //
    // It is a PhysicalComponent, so it inherits part number, material, and the
    // ISO 10993-1 patient-contact characterization that a touched surface needs
    // and that software can never have. That inheritance is why these forms are
    // not UIElement forms: a UIElement is software and cannot state any of it.
    enum def OperatorInterfaceFormKind {
        // ── actuated by the operator ──
        enum knob;
        enum dial;
        enum pushButton;
        enum toggleSwitch;
        enum rockerSwitch;
        enum lever;
        enum physicalSlider;
        enum keypad;
        enum footPedal;
        enum touchSurface;
        // ── presented to the operator ──
        enum indicatorLamp;
        enum gauge;
        enum audibleIndicator;
        enum hapticIndicator;
        enum printedMarking;
    }

    part def OperatorInterfaceElement specializes PhysicalComponent {
        @MemoIdentity { :>> label = "Operator interface element"; }
        attribute formKind : OperatorInterfaceFormKind;
        // actuation (optional; set for actuated forms)
        attribute actuationForce : String;
        attribute actuationTravel : String;
        attribute guardedAgainstInadvertentActuation : Boolean;
        attribute tactileFeedback : String;
        // presentation (optional; set for presented forms)
        attribute legendText : String;
        attribute luminanceOrVolume : String;
    }

    // ─── Captured evidence ───────────────────────────────────────
    // One image of one screen. MemoEvidence, not a design element: it
    // records what a specific build actually displayed at a specific time,
    // which is the provenance a design review or a usability engineering file
    // needs before it can rely on the picture. The screen it depicts is an
    // ordinary UIElement with formKind = screen.
    part def ScreenCapture specializes MemoEvidence {
        @MemoIdentity { :>> label = "Screen capture"; }
        attribute imageUri : String;
        // Content hash of the image bytes. The screenshot is the evidence, so
        // it must be tamper-evident: a DHF reference to a mutable file is not
        // a reference to anything.
        attribute imageHash : String;
        attribute pixelWidth : Integer;
        attribute pixelHeight : Integer;
        attribute captureDate : String;
        // Which build produced this rendering. A screenshot without a build is
        // undated design intent, not evidence of the device.
        attribute capturedBuild : String;
        // Device, viewport, locale, theme, user role — everything that changes
        // what the screen shows without changing the software.
        attribute captureContext : String;
    }

    // UI state is presentation state — distinct from system/device state.
    part def UIState specializes MemoPart {
        @MemoIdentity { :>> label = "UI state"; }
        attribute displayedInformation : String;
        attribute availableActions : String;
    }
    part def UIEvent specializes MemoPart {
        @MemoIdentity { :>> label = "UI event"; }
        attribute eventSource : String;
        attribute intent : InteractionIntentKind;
    }

    // Clicking a button IS an operative action: it has a trigger, a
    // precondition, a criticality, a potential harm and a frequency of use,
    // exactly as turning a knob does. So UIAction specializes OperativeAction:
    // it carries those attributes, and `CommitsUseError` (source end:
    // OperativeAction) accepts a use error committed by a click.
    //
    // The three attributes here are what a UI action adds on top: what the
    // user meant by it, what came back, and whether it asks first.
    action def UIAction specializes OperativeAction {
        @MemoIdentity { :>> label = "UI action"; }
        attribute intent : InteractionIntentKind;
        attribute feedbackProvided : String;
        attribute confirmationRequired : Boolean;
    }

    // A reusable dialogue structure through the UI; a selected path through
    // it is a OperativeScenario with scenarioKind `ui`.
    action def InteractionFlow specializes MemoAction {
        @MemoIdentity { :>> label = "Interaction flow"; }
        attribute entryPoint : String;
        attribute exitPoint : String;
    }

    // `UIState` is a `part def` with plain string attributes, not a `state
    // def`, so `exhibit state` cannot name it: a SysML v2 compiler rejects
    // `exhibit` referencing anything that does not conform to
    // `States::StateAction`. If `UIState` is restructured onto a real state
    // machine, `exhibit state` becomes available.

    // ── Screen layout relations ──────────────────────────────────
    // Which modelled screen an image is a rendering of.
    connection def CapturesScreen :> MemoRelationship {
        @MemoIdentity { :>> label = "Captures screen"; }
        end capture : ScreenCapture :>> source;
        end screen : UIElement :>> target;
    }
    abstract connection capturesScreenLinks : CapturesScreen[*];
    metadata def <capturesScreen> CapturesScreenMetadata :> SemanticMetadata {
        :> annotatedElement : SysML::ConnectionDefinition;
        :> annotatedElement : SysML::ConnectionUsage;
        :>> baseType = capturesScreenLinks meta SysML::Usage;
    }

    // Activating this element opens another screen. This is NAVIGATION, not
    // containment — the opened screen is not laid out inside the element, so it
    // is not a Composes child and the geometric rules do not relate them.
    // "Clicking takes you to a child view" is not spatial nesting: it is a
    // separate frame reached from here, and only this relation says so.
    //
    // connection goToSettings : NavigatesTo connect homeScreen.settingsButton
    // to settingsScreen;
    //
    // A screen is a UIElement whose `formKind` is `screen`; the end says UIElement because the form is an
    // attribute, not a subtype.
    connection def NavigatesTo :> MemoRelationship {
        @MemoIdentity { :>> label = "Navigates to"; }
        end element : UIElement :>> source;
        end screen : UIElement :>> target;
    }
    abstract connection navigatesToLinks : NavigatesTo[*];
    metadata def <navigatesTo> NavigatesToMetadata :> SemanticMetadata {
        :> annotatedElement : SysML::ConnectionDefinition;
        :> annotatedElement : SysML::ConnectionUsage;
        :>> baseType = navigatesToLinks meta SysML::Usage;
    }

    // ── Traceability ─────────────────────────────────────────
    // Source is `MemoPart`, not a UI-specific base: a foot pedal and a
    // rendered button trigger the same kind of action, and the two are a
    // PhysicalComponent and a SoftwareElement whose only common ancestor is
    // MemoPart. CR-MED-111 still holds rendered controls to it, and it is
    // scoped to UIElement, so the wider end does not weaken the rule.
    connection def ElementTriggersAction :> MemoRelationship {
        @MemoIdentity { :>> label = "Element triggers action"; }
        end element : MemoPart :>> source;
        end triggeredAction : UIAction :>> target;
    }
    abstract connection elementTriggersActionLinks : ElementTriggersAction[*];
    metadata def <elementTriggersAction> ElementTriggersActionMetadata :> SemanticMetadata {
        :> annotatedElement : SysML::ConnectionDefinition;
        :> annotatedElement : SysML::ConnectionUsage;
        :>> baseType = elementTriggersActionLinks meta SysML::Usage;
    }
    // A UI action invokes a function by native `perform`: write `perform
    // <systemFunction>;` inside the `UIAction` usage.
    connection def FlowServesUseCase :> MemoRelationship {
        @MemoIdentity { :>> label = "Flow serves use case"; }
        end interactionFlow : InteractionFlow :>> source;
        end useCase : UseCase :>> target;
    }
    abstract connection flowServesUseCaseLinks : FlowServesUseCase[*];
    metadata def <flowServesUseCase> FlowServesUseCaseMetadata :> SemanticMetadata {
        :> annotatedElement : SysML::ConnectionDefinition;
        :> annotatedElement : SysML::ConnectionUsage;
        :>> baseType = flowServesUseCaseLinks meta SysML::Usage;
    }
    // A UI scenario realizes a functional scenario one layer up: each is a
    // OperativeScenario selected by scenarioKind rather than a separate definition.
    // Target is `MemoPart`. IEC 62366-1 scopes the user interface to every
    // means of interaction, so a use error lands wherever the user got it
    // wrong — a mis-keyed connector, a moulded marking, a tube routed
    // backwards — not only on a control. Narrowing this to an interaction
    // base made those unmodellable.
    connection def ErrorAtElement :> MemoRelationship {
        @MemoIdentity { :>> label = "Error at element"; }
        attribute :>> isTrace = true;
        end useError : UseError :>> source;
        end element : MemoPart :>> target;
    }
    abstract connection errorAtElementLinks : ErrorAtElement[*];
    metadata def <errorAtElement> ErrorAtElementMetadata :> SemanticMetadata {
        :> annotatedElement : SysML::ConnectionDefinition;
        :> annotatedElement : SysML::ConnectionUsage;
        :>> baseType = errorAtElementLinks meta SysML::Usage;
    }
    // A risk control implemented by a UI element or by task design
    // (confirmation dialog, lockout, guarded control).
    connection def ControlImplementedBy :> MemoRelationship {
        @MemoIdentity { :>> label = "Control implemented by"; }
        attribute :>> isTrace = true;
        end riskControl : RiskControlMeasure :>> source;
        end implementingElement :>> target;
    }
    abstract connection controlImplementedByLinks : ControlImplementedBy[*];
    metadata def <controlImplementedBy> ControlImplementedByMetadata :> SemanticMetadata {
        :> annotatedElement : SysML::ConnectionDefinition;
        :> annotatedElement : SysML::ConnectionUsage;
        :>> baseType = controlImplementedByLinks meta SysML::Usage;
    }
}
