package memo_assurance_safety_risk_arch_risk {
    private import ScalarValues::*;

    doc /* Configuration Item (CI) aggregator for MEMO architecture risk domain.
         * Re-exports all risk-related packages for Sysand build. */
    public import memo_assurance_safety_risk::*;
}
