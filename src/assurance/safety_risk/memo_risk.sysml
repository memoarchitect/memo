package memo_assurance_safety_risk {
    private import Metaobjects::SemanticMetadata;
    private import ScalarValues::*;
    private import memo_core_relationships::*;   // MemoRelationship

    private import memo_core_common::*;
    private import memo_core_enumerations::*;
    private import memo_assurance_requirements::*;
    // For HazardRelatedScenario below. Assurance may depend on architecture;
    // the reverse is not allowed.
    private import memo_architecture_operational_scenarios::*;

    // ISO 14971 / IEC 62366-1 risk-analysis input. A model element so hazards,
    // scenarios, requirements, and DHF records can trace to the foreseeable
    // misuse that motivated them. Its counterpart, IntendedUse, is now the
    // operational-world root (memo_architecture_operational_structure::IntendedUse,
    // a MemoMission).
    part def ReasonablyForeseeableMisuse specializes MemoPart {
        @MemoIdentity { :>> label = "Reasonably foreseeable misuse"; }
        attribute misuseContext : String;
        attribute foreseeableBasis : String;
        attribute affectedUseContext : String;
    }

    part def Risk specializes RiskDriver {
        @MemoIdentity { :>> label = "Risk"; }
        attribute probabilityEstimate : ProbabilityKind;
        attribute severityEstimate : SeverityKind;
        attribute riskLevel : CriticalityKind;
        attribute acceptability : RiskAcceptabilityKind;
        attribute estimationBasis : String;
        attribute analysisContext : String;
        attribute foreseeableMisuseIncluded : Boolean;
        doc /* The risk that remains after the controls (ISO 14971 clause 7) is the same risk
             * re-estimated, so a register that holds one row per risk states it here. A
             * ResidualRisk part is for a model that evaluates it as an element of its own. */
        attribute residualProbabilityEstimate : ProbabilityKind[0..1];
        attribute residualSeverityEstimate : SeverityKind[0..1];
        attribute residualBenefitRiskRequired : Boolean[0..1];
    }
    part def ResidualRisk specializes Risk {
        @MemoIdentity { :>> label = "Residual risk"; }
        attribute benefitRiskRequired : Boolean;
    }
    part def RiskMatrix specializes MemoPart {
        @MemoIdentity { :>> label = "Risk matrix"; }
        attribute probabilityScaleDefinition : String;
        attribute severityScaleDefinition : String;
        attribute riskLevelMapping : String;
        attribute acceptabilityThresholds : String;
    }
    // A risk decomposes into the ISO 14971 chain below: a Hazard,
    // SequenceOfEvents, HazardousSituation and Harm are independent elements,
    // not owned by a risk, because the same hazard is the hazard of many risks.
    // A Risk is linked to each by EstimatedFor, and the chain runs through
    // TracesRisk / LeadsToHarm, with ResidualRisk after mitigation. The risk
    // itself is reached by EstimatedFor / ReducedBy / EvaluatedIn below. A
    // device characteristic whose implementation, failure, or misuse can affect
    // safety. This is the modelable output of ISO 14971 §5.3.
    part def SafetyRelatedCharacteristic specializes MemoPart {
        @MemoIdentity { :>> label = "Safety related characteristic"; }
        attribute characteristic : String;
        attribute safetyImpact : String;
        attribute normalUseRelevant : Boolean;
        attribute faultConditionRelevant : Boolean;
    }
    // ─── Risk-element base ──────────────────────────────────────────
    // The common supertype of the item-based elements an ISO 14971 / FMEA /
    // FTA chain relates: hazards, sequences of events, hazardous situations,
    // harms, causes, failure modes, fault-tree events, cut sets, HAZOP
    // deviations, vulnerabilities.
    //
    // It exists so the risk relations can TYPE their ends. Before it, every
    // one of them (Causes, TracesRisk, DetectedBy, InputToGate, ProducesEvent,
    // ContainsEvent, IdentifiesHazard, Mitigates, ImpactsSafety) fell back to
    // MemoPart — which every element in MEMO is — so the authoring picker
    // offered fault-tree edges when linking a screen to a requirement.
    //
    // It is deliberately an `item def` and deliberately does NOT cover Risk /
    // ResidualRisk / RiskMatrix, which are parts: a risk is an assessed
    // judgement about a chain, not a link in it, and it is reached by
    // AssessedAgainst instead. One base per metaclass is the right shape here
    // — forcing the two families under one supertype would put a hazard and a
    // risk matrix back in the same picker.
    abstract item def RiskItem specializes MemoItem {
        @MemoIdentity { :>> label = "Risk item"; }
    }

    item def Hazard specializes RiskItem {
        @MemoIdentity { :>> label = "Hazard"; }
        attribute hazardType : HazardTypeKind;
        attribute severity : SeverityKind;
        attribute foreseeable : Boolean;
    }
    item def SequenceOfEvents specializes RiskItem {
        @MemoIdentity { :>> label = "Sequence of events"; }
        attribute initiatingEvent : String;
        attribute contributingFactors : String;
    }
    // A categorized root cause in a hazard causal tree (FDA GIIP
    // taxonomy pattern: cause -> hazard -> hazardous situation -> harm;
    // several HazardCause elements may converge on one Hazard).
    item def HazardCause specializes RiskItem {
        @MemoIdentity { :>> label = "Hazard cause"; }
        attribute causeSource : CauseSourceKind;
        attribute contributingFactors : String;
    }
    item def HazardousSituation specializes RiskItem {
        @MemoIdentity { :>> label = "Hazardous situation"; }
        attribute exposedPersons : String;
        attribute operatingCondition : String;
        // ISO 14971 P1: probability that the hazardous situation occurs.
        attribute probabilityOfOccurrence : ProbabilityKind;
    }
    item def Harm specializes RiskItem {
        @MemoIdentity { :>> label = "Harm"; }
        attribute clinicalImpact : String;
        attribute reversibility : String;
        attribute severity : SeverityKind;
    }
    part def RiskControlMeasure specializes VerifiableElement {
        @MemoIdentity { :>> label = "Risk control measure"; }
        attribute controlKind : RiskControlKind;
        attribute implementationKind : RiskControlImplementationKind;
        attribute verificationStatus : String;
    }
    part def Benefit specializes MemoPart {
        @MemoIdentity { :>> label = "Benefit"; }
        attribute beneficialOutcome : String;
        attribute beneficiary : String;
        attribute clinicalSignificance : String;
        attribute supportingEvidence : String;
    }
    part def OverallResidualRiskEvaluation specializes MemoPart {
        @MemoIdentity { :>> label = "Overall residual risk evaluation"; }
        attribute conclusion : String;
        attribute reviewer : String;
    }

    // ── Relations owned by this package ─────────────────────────────
    // Moved out of memo_core_relationships: their ends are typed against
    // types declared here, and core must not depend on a domain package.
    // ISO 14971 risk chain — distinct sequence-of-events relations over risk elements.
    connection def TracesRisk :> MemoRelationship {
        @MemoIdentity { :>> label = "Traces risk"; }
        attribute :>> isTrace = true;
        end sourceRiskElement : RiskItem :>> source;
        end targetRiskElement : RiskItem :>> target;
    }
    abstract connection tracesRiskLinks : TracesRisk[*];
    metadata def <tracesRisk> TracesRiskMetadata :> SemanticMetadata {
        :> annotatedElement : SysML::ConnectionDefinition;
        :> annotatedElement : SysML::ConnectionUsage;
        :>> baseType = tracesRiskLinks meta SysML::Usage;
    }
    // The final ISO 14971 chain edge. P2 is the conditional probability that
    // the hazardous situation results in the harm.
    connection def LeadsToHarm :> MemoRelationship {
        @MemoIdentity { :>> label = "Leads to harm"; }
        attribute conditionalProbability : ProbabilityKind;
        end hazardousSituation : HazardousSituation :>> source;
        end resultingHarm : Harm :>> target;
    }
    abstract connection leadsToHarmLinks : LeadsToHarm[*];
    metadata def <leadsToHarm> LeadsToHarmMetadata :> SemanticMetadata {
        :> annotatedElement : SysML::ConnectionDefinition;
        :> annotatedElement : SysML::ConnectionUsage;
        :>> baseType = leadsToHarmLinks meta SysML::Usage;
    }
    // IEC 62366-1 3.9's hazard-related use scenario: the scenario a hazard can
    // arise in. It is declared HERE because assurance may depend on
    // architecture, and the scenario package cannot see `Hazard`. On this side
    // both ends are visible.
    connection def HazardRelatedScenario :> MemoRelationship {
        @MemoIdentity { :>> label = "Hazard related scenario"; }
        attribute :>> isTrace = true;
        end hazard : RiskItem :>> source;
        end scenario : OperativeScenario :>> target;
    }
    abstract connection hazardRelatedScenarioLinks : HazardRelatedScenario[*];
    metadata def <hazardRelatedScenario> HazardRelatedScenarioMetadata :> SemanticMetadata {
        :> annotatedElement : SysML::ConnectionDefinition;
        :> annotatedElement : SysML::ConnectionUsage;
        :>> baseType = hazardRelatedScenarioLinks meta SysML::Usage;
    }
    connection def AssessedAgainst :> MemoRelationship {
        @MemoIdentity { :>> label = "Assessed against"; }
        end risk : Risk :>> source;
        end riskMatrix : RiskMatrix :>> target;
    }
    abstract connection assessedAgainstLinks : AssessedAgainst[*];
    metadata def <assessedAgainst> AssessedAgainstMetadata :> SemanticMetadata {
        :> annotatedElement : SysML::ConnectionDefinition;
        :> annotatedElement : SysML::ConnectionUsage;
        :>> baseType = assessedAgainstLinks meta SysML::Usage;
    }
    // A risk is not a link in the chain (see RiskItem), so TracesRisk cannot
    // reach it. These three say which hazardous situation or harm a risk was
    // estimated for (ISO 14971 §5.5), which control reduced it to a residual
    // risk (§7), and which overall evaluation covered that residual (§8). Named
    // from the risk's side, like AssessedAgainst.
    connection def EstimatedFor :> MemoRelationship {
        @MemoIdentity { :>> label = "Estimated for"; }
        end risk : Risk :>> source;
        end riskElement : RiskItem :>> target;
    }
    abstract connection estimatedForLinks : EstimatedFor[*];
    metadata def <estimatedFor> EstimatedForMetadata :> SemanticMetadata {
        :> annotatedElement : SysML::ConnectionDefinition;
        :> annotatedElement : SysML::ConnectionUsage;
        :>> baseType = estimatedForLinks meta SysML::Usage;
    }
    connection def ReducedBy :> MemoRelationship {
        @MemoIdentity { :>> label = "Reduced by"; }
        end residualRisk : ResidualRisk :>> source;
        end control : RiskControlMeasure :>> target;
    }
    abstract connection reducedByLinks : ReducedBy[*];
    metadata def <reducedBy> ReducedByMetadata :> SemanticMetadata {
        :> annotatedElement : SysML::ConnectionDefinition;
        :> annotatedElement : SysML::ConnectionUsage;
        :>> baseType = reducedByLinks meta SysML::Usage;
    }
    connection def EvaluatedIn :> MemoRelationship {
        @MemoIdentity { :>> label = "Evaluated in"; }
        end residualRisk : ResidualRisk :>> source;
        end evaluation : OverallResidualRiskEvaluation :>> target;
    }
    abstract connection evaluatedInLinks : EvaluatedIn[*];
    metadata def <evaluatedIn> EvaluatedInMetadata :> SemanticMetadata {
        :> annotatedElement : SysML::ConnectionDefinition;
        :> annotatedElement : SysML::ConnectionUsage;
        :>> baseType = evaluatedInLinks meta SysML::Usage;
    }
    // Mitigates unifies the control/action → risk-element edges of the
    // ISO 14971 / FMEA / FTA / cyber chains — MitigatesHazard,
    // MitigatesVulnerability, MitigatedByControl, BrokenByControl,
    // AddressedByAction — keyed by mitigationKind. control is the mitigating
    // control/action; mitigatedElement is the hazard/vulnerability/failure/cut set.
    enum def MitigationKind {
        enum hazard;
        enum vulnerability;
        enum failureMode;
        enum cutSet;
        enum fmeaAction;
    }
    connection def Mitigates :> MemoRelationship {
        @MemoIdentity { :>> label = "Mitigates"; }
        attribute :>> isTrace = true;
        attribute mitigationKind : MitigationKind;
        // Untyped: controls/hazards may be item defs (RiskControlMeasure, Hazard, …).
        end control :>> source;
        end mitigatedElement : RiskItem :>> target;
    }
    abstract connection mitigatesLinks : Mitigates[*];
    metadata def <mitigates> MitigatesMetadata :> SemanticMetadata {
        :> annotatedElement : SysML::ConnectionDefinition;
        :> annotatedElement : SysML::ConnectionUsage;
        :>> baseType = mitigatesLinks meta SysML::Usage;
    }

    // ISO 14971 clause 7.4: where the residual risk is judged unacceptable, the benefit of the intended use is
    // weighed against it. Nothing in the chain reached a Benefit, which is a part and not a RiskItem, and the
    // generic relations that accept the pair say something else (`causes` between a benefit and a risk would say
    // the benefit gives rise to it). Named from the benefit's side, the way AssessedAgainst is from the risk's.
    connection def WeighedAgainst :> MemoRelationship {
        @MemoIdentity { :>> label = "Weighed against"; }
        end benefit : Benefit :>> source;
        end risk : Risk :>> target;
    }
    abstract connection weighedAgainstLinks : WeighedAgainst[*];
    metadata def <weighedAgainst> WeighedAgainstMetadata :> SemanticMetadata {
        :> annotatedElement : SysML::ConnectionDefinition;
        :> annotatedElement : SysML::ConnectionUsage;
        :>> baseType = weighedAgainstLinks meta SysML::Usage;
    }
}
