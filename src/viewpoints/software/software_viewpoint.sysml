package memo_viewpoints_software_software_viewpoint {
    private import ScalarValues::*;

    private import memo_viewpoints_definitions::*;
    private import memo_core_enumerations::*;
    private import memo_viewpoints_stakeholders_concerns::*;

    private import memo_core_common::*;
    viewpoint softwareViewpoint : MemoViewpoint {
        @MemoIdentity { :>> providedId = "VP-SW"; :>> label = "SoftwareViewpoint"; }
        doc /* Default viewpoint derived from the software structure layer for IEC 62304 software architecture description — software item decomposition, SOUP inventory, and software-to-software interfaces, distinct from system-level logical decomposition. */
        @MemoIdentity { :>> shortDescription = "Shows software systems, components, SOUP, and software interfaces."; }
        attribute :>> purpose = "Describe the software architecture for IEC 62304 design documentation.";
        ref :>> memoStakeholders = (softwareArchitect);
        attribute :>> stage = WorkflowStageKind::architecture;
        attribute :>> abstractionLevel = "software";
        attribute :>> outputKind = (ViewOutputKind::diagram);
        attribute :>> presentationKind = (PresentationKind::blockDiagram);
        ref :>> framedConcerns = (safetyConcern, reliabilityConcern);
        attribute :>> explorerLane = "architecture";
        attribute :>> explorerOrder = 4;
        attribute :>> userExtensible = true;
    }
}
