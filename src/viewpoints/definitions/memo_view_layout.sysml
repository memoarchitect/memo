// Where a view's boxes sit. A drawing's layout is presentation, and it is
// written in the view that owns it: `@MemoLayout` and its `@MemoLayout*`
// siblings annotate a `view` usage (their `annotatedElement` is never anything
// else), inside the view's own body. That way the compiler, review and a pinned
// build can all see it.
//
// Flat on purpose. Each box, port, connector route and note is one metadata
// usage with primitive values, because a metadata body can redefine an
// attribute with a literal (MetadataBodyUsage, SysML-textual-bnf.kebnf:1694)
// but cannot construct a nested record, and a repeated record needs one usage
// per instance. Elements are named by their qualified id as a STRING, not a
// reference: a layout is not a model fact, so it must not become a
// relationship, and a reference to a renamed element would break the compile
// where a stale string only returns that box to automatic placement.
//
// The camera (zoom and pan) is not stored. It is one person's window onto the
// drawing, not the drawing, and recording it would put a diff in the model
// every time someone scrolled.
package memo_viewpoints_definitions_layout {
    private import ScalarValues::*;

    enum def MemoLayoutSide {
        enum top;
        enum bottom;
        enum left;
        enum right;
    }

    enum def MemoLayoutLineStyle {
        enum solid;
        enum dashed;
        enum dotted;
    }

    enum def MemoLayoutAlign {
        enum left;
        enum center;
        enum right;
    }

    enum def MemoLayoutVerticalAlign {
        enum top;
        enum middle;
        enum bottom;
    }

    /** The view-wide choices. One per view, absent when the view keeps every default. */
    metadata def MemoLayout {
        :> annotatedElement : SysML::ViewUsage;
        /** False once a person has placed a box by hand. */
        attribute autoLayout : Boolean[0..1];
        attribute grid : Real[0..1];
        attribute snap : Boolean[0..1];
        /**
         * The positions were written in a coordinate frame that differs from the
         * current one; `context-child-v1` says a nested box's position is
         * relative to its parent, as the canvas stores it now.
         */
        attribute coordinateSpace : String[0..1];
        /** The automatic-layout provider the person chose for this view, and the version of it that placed the boxes. */
        attribute layoutProvider : String[0..1];
        attribute layoutProviderVersion : String[0..1];
        attribute layoutContractVersion : String[0..1];
        attribute layoutPreset : String[0..1];
        attribute layoutSeed : Real[0..1];
        /** How this view's connectors are drawn, and whether they follow the router or a person. */
        attribute routingType : String[0..1];
        attribute routingMode : String[0..1];
    }

    /** Renderer namespaces and forward-compatible presentation fields only.
     * Standard geometry remains in the typed MemoLayout* records. The JSON
     * envelope is versioned by its writer; this string creates no model links.
     */
    metadata def MemoLayoutExtension {
        :> annotatedElement : SysML::ViewUsage;
        attribute payload : String;
    }

    /**
     * One box. `x` and `y` are in the frame of `parentElement` (the box it is
     * nested in), or on the board when there is none; the frame is recorded
     * because a box that changes nesting would otherwise be read in the wrong
     * one and jump.
     */
    metadata def MemoLayoutNode {
        :> annotatedElement : SysML::ViewUsage;
        attribute element : String;
        attribute parentElement : String[0..1];
        attribute x : Real;
        attribute y : Real;
        attribute width : Real[0..1];
        attribute height : Real[0..1];
        attribute fillColor : String[0..1];
        attribute borderColor : String[0..1];
        attribute textColor : String[0..1];
        attribute fontSize : Real[0..1];
        attribute fontWeight : Real[0..1];
        attribute textAlign : MemoLayoutAlign[0..1];
        attribute verticalAlign : MemoLayoutVerticalAlign[0..1];
        attribute opacity : Real[0..1];
    }

    /** Where a boundary port sits on its owner's box, relative to that box. */
    metadata def MemoLayoutPort {
        :> annotatedElement : SysML::ViewUsage;
        attribute element : String;
        attribute portName : String;
        attribute x : Real;
        attribute y : Real;
        attribute side : MemoLayoutSide[0..1];
        attribute size : Real[0..1];
        /** A port nested in a port: how far along its parent, and whether it faces out. */
        attribute alongOffset : Real[0..1];
        attribute faceOuter : Boolean[0..1];
    }

    /**
     * Which wall a boundary port straddles. A constraint rather than a
     * position: automatic layout still places the port, on that wall.
     */
    metadata def MemoLayoutPortWall {
        :> annotatedElement : SysML::ViewUsage;
        attribute portId : String;
        attribute wall : MemoLayoutSide;
    }

    /**
     * A connector's presentation. `route` is the hand-drawn bend points as
     * x, y, x, y, … in board coordinates; the landings say where each end meets
     * its box, as a wall and a fraction along it, and survive the box moving.
     */
    metadata def MemoLayoutEdge {
        :> annotatedElement : SysML::ViewUsage;
        attribute edge : String;
        attribute color : String[0..1];
        attribute strokeWidth : Real[0..1];
        attribute labelVisible : Boolean[0..1];
        attribute lineStyle : MemoLayoutLineStyle[0..1];
        attribute route : Real[0..*] ordered nonunique;
        /** A short token for the connector's ends, so a route is kept only while it still joins what it was drawn between. */
        attribute attachment : String[0..1];
        attribute sourceElement : String[0..1];
        attribute targetElement : String[0..1];
        attribute sourcePortId : String[0..1];
        attribute targetPortId : String[0..1];
        attribute manualLanding : Boolean[0..1];
        attribute sourceSide : MemoLayoutSide[0..1];
        attribute sourceT : Real[0..1];
        attribute targetSide : MemoLayoutSide[0..1];
        attribute targetT : Real[0..1];
        /**
         * False when the router computed `route`, so the next routing may replace it.
         * A route is stored because routing a whole board on every open is too slow.
         */
        attribute manualRoute : Boolean[0..1];
        attribute routingType : String[0..1];
        attribute routingOverride : String[0..1];
        /** Where the connector's label sits, on the board. */
        attribute labelX : Real[0..1];
        attribute labelY : Real[0..1];
        /** Where each end leaves its box, relative to the box, and on which wall. */
        attribute sourceOffsetX : Real[0..1];
        attribute sourceOffsetY : Real[0..1];
        attribute sourceOffsetSide : MemoLayoutSide[0..1];
        attribute targetOffsetX : Real[0..1];
        attribute targetOffsetY : Real[0..1];
        attribute targetOffsetSide : MemoLayoutSide[0..1];
    }

    /** A note, text label or constraint box that belongs to the drawing and not to the model. */
    metadata def MemoLayoutNote {
        :> annotatedElement : SysML::ViewUsage;
        attribute noteId : String;
        attribute noteKind : String;
        attribute x : Real;
        attribute y : Real;
        attribute width : Real[0..1];
        attribute height : Real[0..1];
        attribute text : String;
        attribute fillColor : String[0..1];
    }
}
