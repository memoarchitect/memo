// Stakeholders and concerns, as elements.
//
// ISO/IEC/IEEE 42010 gives a viewpoint three jobs: name the stakeholders, frame
// their concerns, and be what a view conforms to.
//
// They are elements, so a concern can have an id, a holder and a trace. SysML
// v2 already models both — `ConcernDefinition` and `StakeholderMembership` are
// in the metamodel — so nothing new is invented here. Each carries
// `@MemoIdentity`, which is what makes it citable in a review the way every
// other MEMO element is.
package memo_viewpoints_stakeholders_concerns {
    private import ScalarValues::*;
    private import memo_core_common::*;

    // ─── Concerns ────────────────────────────────────────────────────────
    //
    // A concern is an interest in the system held by one or more stakeholders.
    // `concern def` is the native SysML construct for it; a viewpoint frames
    // the concerns it addresses.
    //
    // It extends the standard concern's `stakeholders` (the Parts interested in
    // it) to the MEMO stakeholder catalog, as a viewpoint does for its own.
    abstract concern def MemoConcern {
        @MemoIdentity { :>> label = "Concern"; }
        ref memoStakeholders :>> stakeholders : MemoStakeholder[0..*];
    }

    concern def SafetyConcern :> MemoConcern {
        doc /* Freedom from unacceptable risk of harm to the patient, the operator or a bystander. */
        @MemoIdentity { :>> label = "Safety"; :>> providedId = "CNC-1"; }
    }
    concern def UsabilityConcern :> MemoConcern {
        doc /* Whether the intended user can operate the device correctly under use conditions. */
        @MemoIdentity { :>> label = "Usability"; :>> providedId = "CNC-2"; }
    }
    concern def CybersecurityConcern :> MemoConcern {
        doc /* Resistance to compromise of the device, its data, or the network it participates in. */
        @MemoIdentity { :>> label = "Cybersecurity"; :>> providedId = "CNC-3"; }
    }
    concern def PerformanceConcern :> MemoConcern {
        doc /* Timing, throughput and capacity against what the clinical procedure demands. */
        @MemoIdentity { :>> label = "Performance"; :>> providedId = "CNC-4"; }
    }
    concern def InteroperabilityConcern :> MemoConcern {
        doc /* Correct exchange with the equipment and systems the device is used alongside. */
        @MemoIdentity { :>> label = "Interoperability"; :>> providedId = "CNC-5"; }
    }
    concern def ReliabilityConcern :> MemoConcern {
        doc /* Continuity of correct service, and behaviour on failure. */
        @MemoIdentity { :>> label = "Reliability"; :>> providedId = "CNC-6"; }
    }
    concern def PrivacyConcern :> MemoConcern {
        doc /* Protection of patient and operator data through its lifecycle. */
        @MemoIdentity { :>> label = "Privacy"; :>> providedId = "CNC-7"; }
    }
    concern def RegulatoryConcern :> MemoConcern {
        doc /* Evidence a submission requires, and conformance to the standards claimed. */
        @MemoIdentity { :>> label = "Regulatory"; :>> providedId = "CNC-8"; }
    }
    concern def ClinicalConcern :> MemoConcern {
        doc /* Whether the device serves the clinical procedure and its intended use. */
        @MemoIdentity { :>> label = "Clinical"; :>> providedId = "CNC-9"; }
    }

    // ─── Quality attributes ──────────────────────────────────────────────
    //
    // A concern is what a stakeholder cares about; a quality attribute is the
    // measurable property of the system through which that care is answered.
    // The SEI's separation (Bass, Clements & Kazman): "performance" as a
    // concern is a worry, and only becomes designable once it is stated as a
    // property with a stimulus, a response and a measure.
    //
    // `addressesConcerns` is the mapping, and it is many-to-many on purpose.
    // Availability answers safety AND clinical continuity; security answers
    // cybersecurity AND privacy. A quality attribute that addresses no concern
    // is one nobody asked for, and a concern with no quality attribute behind
    // it is a worry the architecture has not yet answered — both are findings
    // this mapping makes visible.
    abstract part def MemoQualityAttribute :> MemoPart {
        @MemoIdentity { :>> label = "Quality attribute"; }
        ref addressesConcerns : MemoConcern[*];
        /** How the property is measured — the response measure of a quality
         *  attribute scenario, stated once for the attribute. */
        attribute measure : String;
    }

    part def Availability :> MemoQualityAttribute {
        @MemoIdentity { :>> label = "Availability"; :>> providedId = "QA-1"; }
        ref :>> addressesConcerns = (safetyConcern, reliabilityConcern, clinicalConcern);
        attribute :>> measure = "Proportion of scheduled procedure time the function is delivered, and time to recover after a fault.";
    }
    part def Performance :> MemoQualityAttribute {
        @MemoIdentity { :>> label = "Performance"; :>> providedId = "QA-2"; }
        ref :>> addressesConcerns = (performanceConcern, clinicalConcern);
        attribute :>> measure = "Latency and throughput under the arrival pattern the procedure produces.";
    }
    part def Security :> MemoQualityAttribute {
        @MemoIdentity { :>> label = "Security"; :>> providedId = "QA-3"; }
        ref :>> addressesConcerns = (cybersecurityConcern, privacyConcern, safetyConcern);
        attribute :>> measure = "Resistance to a stated threat, and time to detect and recover from a compromise.";
    }
    part def Modifiability :> MemoQualityAttribute {
        @MemoIdentity { :>> label = "Modifiability"; :>> providedId = "QA-4"; }
        ref :>> addressesConcerns = (regulatoryConcern);
        attribute :>> measure = "Cost and blast radius of a stated change, including the re-verification it forces.";
    }
    part def Testability :> MemoQualityAttribute {
        @MemoIdentity { :>> label = "Testability"; :>> providedId = "QA-5"; }
        ref :>> addressesConcerns = (regulatoryConcern, safetyConcern);
        attribute :>> measure = "Probability that a fault present is revealed by the next test, and the effort to observe it.";
    }
    part def Usability :> MemoQualityAttribute {
        @MemoIdentity { :>> label = "Usability"; :>> providedId = "QA-6"; }
        ref :>> addressesConcerns = (usabilityConcern, safetyConcern, clinicalConcern);
        attribute :>> measure = "Task success and use-error rate for the intended user under use conditions (IEC 62366-1).";
    }
    part def Interoperability :> MemoQualityAttribute {
        @MemoIdentity { :>> label = "Interoperability"; :>> providedId = "QA-7"; }
        ref :>> addressesConcerns = (interoperabilityConcern, clinicalConcern);
        attribute :>> measure = "Proportion of exchanges with a named partner system that are correctly understood.";
    }

    // ─── Stakeholders ────────────────────────────────────────────────────
    //
    // A stakeholder holds concerns. These are the engineering and regulatory
    // roles a viewpoint is written FOR; the clinical actors who operate the
    // device are OperationalParticipants and are a different population.
    //
    // SysML v2 has no stakeholder definition to specialize: a stakeholder is a
    // `Part` that a concern or viewpoint lists in `RequirementCheck::stakeholders`
    // (declared with a `stakeholder` member). So the catalog is standard parts,
    // not `MemoPart`s — MemoPart's lifecycle and dimension attributes describe
    // model elements, not the people a viewpoint is written for.
    abstract part def MemoStakeholder :> Parts::Part {
        @MemoIdentity { :>> label = "Stakeholder"; }
    }

    part def SystemArchitect :> MemoStakeholder {
        @MemoIdentity { :>> providedId = "STK-1"; :>> label = "System Architect"; }
    }
    part def SoftwareArchitect :> MemoStakeholder {
        @MemoIdentity { :>> providedId = "STK-2"; :>> label = "Software Architect"; }
    }
    part def HardwareEngineer :> MemoStakeholder {
        @MemoIdentity { :>> providedId = "STK-3"; :>> label = "Hardware Engineer"; }
    }
    part def SafetyEngineer :> MemoStakeholder {
        @MemoIdentity { :>> providedId = "STK-4"; :>> label = "Safety Engineer"; }
    }
    part def VerificationEngineer :> MemoStakeholder {
        @MemoIdentity { :>> providedId = "STK-5"; :>> label = "Verification Engineer"; }
    }
    part def RegulatoryEngineer :> MemoStakeholder {
        @MemoIdentity { :>> providedId = "STK-6"; :>> label = "Regulatory Engineer"; }
    }
    part def ProjectLead :> MemoStakeholder {
        @MemoIdentity { :>> providedId = "STK-7"; :>> label = "Project Lead"; }
    }
    part def SecurityEngineer :> MemoStakeholder {
        @MemoIdentity { :>> providedId = "STK-8"; :>> label = "Security Engineer"; }
    }
    part def PrivacyEngineer :> MemoStakeholder {
        @MemoIdentity { :>> providedId = "STK-9"; :>> label = "Privacy Engineer"; }
    }
    part def ClinicalEngineer :> MemoStakeholder {
        @MemoIdentity { :>> providedId = "STK-10"; :>> label = "Clinical Engineer"; }
    }
    part def UsabilityEngineer :> MemoStakeholder {
        @MemoIdentity { :>> providedId = "STK-11"; :>> label = "Usability Engineer"; }
    }

    // ─── The catalog, as usages ─────────────────────────────────────────
    //
    // A viewpoint's `memoStakeholders` and `framedConcerns`, and a quality
    // attribute's `addressesConcerns`, are features. What a feature is bound to
    // has to be a feature as well, not a definition, so each concern and each
    // stakeholder above has exactly one usage for those bindings to name.
    concern safetyConcern : SafetyConcern;
    concern usabilityConcern : UsabilityConcern;
    concern cybersecurityConcern : CybersecurityConcern;
    concern performanceConcern : PerformanceConcern;
    concern interoperabilityConcern : InteroperabilityConcern;
    concern reliabilityConcern : ReliabilityConcern;
    concern privacyConcern : PrivacyConcern;
    concern regulatoryConcern : RegulatoryConcern;
    concern clinicalConcern : ClinicalConcern;
    part systemArchitect : SystemArchitect;
    part softwareArchitect : SoftwareArchitect;
    part hardwareEngineer : HardwareEngineer;
    part safetyEngineer : SafetyEngineer;
    part verificationEngineer : VerificationEngineer;
    part regulatoryEngineer : RegulatoryEngineer;
    part projectLead : ProjectLead;
    part securityEngineer : SecurityEngineer;
    part privacyEngineer : PrivacyEngineer;
    part clinicalEngineer : ClinicalEngineer;
    part usabilityEngineer : UsabilityEngineer;
}
