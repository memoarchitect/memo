package memo_viewpoints_cybersecurity_views_threat_model_view {
    private import ScalarValues::*;
    private import memo_core_common::MemoIdentity;

    private import memo_viewpoints_definitions::*;
    private import memo_core_enumerations::*;

    view def MemoCybersecurityThreatModelView :> MemoDocumentView {
        @MemoIdentity { :>> label = "Cybersecurity threat model view"; }
        attribute :>> viewKind = DocumentViewKind::threatModel;
        attribute :>> generationRule = "Include assets, trust boundaries, threat scenarios, vulnerabilities, mitigations, and trace links to safety/privacy concerns.";
        attribute :>> outputKind = (ViewOutputKind::documentSection);
        attribute :>> presentationKind = (PresentationKind::narrativeSection);
    }
}
