package memo_viewpoints_operational_operational_viewpoint {
    private import ScalarValues::*;

    private import memo_viewpoints_definitions::*;
    private import memo_core_enumerations::*;
    private import memo_viewpoints_stakeholders_concerns::*;

    private import memo_core_common::*;
    viewpoint operationalViewpoint : MemoViewpoint {
        @MemoIdentity { :>> providedId = "VP-OPS"; :>> label = "OperationalViewpoint"; }
        doc /* Default viewpoint derived from the context, operational, and system layers for how actors use the device — operational scenarios, capabilities, and the functional chains that realize them. */
        @MemoIdentity { :>> shortDescription = "Shows actors, use contexts, operational scenarios, and system capabilities."; }
        attribute :>> purpose = "Communicate how actors interact with the system and which capabilities they invoke.";
        ref :>> memoStakeholders = (projectLead, systemArchitect);
        attribute :>> stage = WorkflowStageKind::context;
        attribute :>> abstractionLevel = "operational";
        attribute :>> outputKind = (ViewOutputKind::diagram);
        attribute :>> presentationKind = (PresentationKind::custom);
        ref :>> framedConcerns = (performanceConcern, interoperabilityConcern);
        attribute :>> explorerLane = "architecture";
        attribute :>> explorerOrder = 1;
        attribute :>> userExtensible = true;
    }
}
