package memo_viewpoints_clinical_clinical_viewpoint {
    private import ScalarValues::*;

    private import memo_viewpoints_definitions::*;
    private import memo_core_enumerations::*;
    private import memo_viewpoints_stakeholders_concerns::*;

    private import memo_core_common::*;
    viewpoint clinicalViewpoint : MemoViewpoint {
        @MemoIdentity { :>> providedId = "VP-CLIN"; :>> label = "ClinicalViewpoint"; }
        doc /* Default viewpoint derived from the context and assurance layers for clinical stakeholders — intended use, patient/clinician interaction, clinical evidence, and clinical safety claims. */
        @MemoIdentity { :>> shortDescription = "Shows clinical context, users, use environment, and clinical evidence."; }
        attribute :>> purpose = "Communicate clinical use context and clinical evidence for the device.";
        ref :>> memoStakeholders = (clinicalEngineer, regulatoryEngineer);
        attribute :>> stage = WorkflowStageKind::context;
        attribute :>> abstractionLevel = "clinical";
        attribute :>> outputKind = (ViewOutputKind::documentSection, ViewOutputKind::table);
        attribute :>> presentationKind = (PresentationKind::narrativeSection);
        ref :>> framedConcerns = (safetyConcern, clinicalConcern);
        attribute :>> explorerLane = "assurance";
        attribute :>> explorerOrder = 4;
        attribute :>> userExtensible = true;
    }
}
