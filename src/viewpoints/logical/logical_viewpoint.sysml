package memo_viewpoints_logical_logical_viewpoint {
    private import ScalarValues::*;

    private import memo_viewpoints_definitions::*;
    private import memo_core_enumerations::*;
    private import memo_viewpoints_stakeholders_concerns::*;

    private import memo_core_common::*;
    viewpoint logicalArchitectureViewpoint : MemoViewpoint {
        @MemoIdentity { :>> providedId = "VP-LOG"; :>> label = "LogicalArchitectureViewpoint"; }
        doc /* Default viewpoint derived from the logical architecture layer for subsystem structure, responsibilities, and major interactions, independent of physical realization. */
        @MemoIdentity { :>> shortDescription = "Shows logical decomposition and interfaces."; }
        attribute :>> purpose = "Describe the system's logical decomposition.";
        ref :>> memoStakeholders = (systemArchitect);
        attribute :>> stage = WorkflowStageKind::architecture;
        attribute :>> abstractionLevel = "logical";
        attribute :>> outputKind = (ViewOutputKind::diagram);
        attribute :>> presentationKind = (PresentationKind::blockDiagram);
        ref :>> framedConcerns = (safetyConcern, performanceConcern);
        attribute :>> explorerLane = "architecture";
        attribute :>> explorerOrder = 3;
        attribute :>> userExtensible = true;
    }
}
