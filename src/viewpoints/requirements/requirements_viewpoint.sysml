package memo_viewpoints_requirements_requirements_viewpoint {
    private import ScalarValues::*;

    private import memo_viewpoints_definitions::*;
    private import memo_core_enumerations::*;
    private import memo_viewpoints_stakeholders_concerns::*;

    private import memo_core_common::*;
    viewpoint requirementsViewpoint : MemoViewpoint {
        @MemoIdentity { :>> providedId = "VP-REQ"; :>> label = "RequirementsViewpoint"; }
        doc /* Default viewpoint derived from the requirements layer for requirements traceability — the chain from stakeholder need through system, software, and hardware requirements, supporting IEC 62304 §5.1.1 and ISO 13485 §7.3.3. */
        @MemoIdentity { :>> shortDescription = "Shows stakeholder needs and their decomposition into system, software, and hardware requirements."; }
        attribute :>> purpose = "Communicate requirements decomposition and traceability.";
        ref :>> memoStakeholders = (regulatoryEngineer, systemArchitect);
        attribute :>> stage = WorkflowStageKind::requirements;
        attribute :>> abstractionLevel = "requirements";
        attribute :>> outputKind = (ViewOutputKind::diagram, ViewOutputKind::matrix);
        attribute :>> presentationKind = (PresentationKind::traceMatrix);
        ref :>> framedConcerns = (regulatoryConcern, safetyConcern);
        attribute :>> explorerLane = "assurance";
        attribute :>> explorerOrder = 1;
        attribute :>> userExtensible = true;
    }
}
