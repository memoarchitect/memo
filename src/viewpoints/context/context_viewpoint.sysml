package memo_viewpoints_context_context_viewpoint {
    private import ScalarValues::*;

    private import memo_viewpoints_definitions::*;
    private import memo_core_enumerations::*;
    private import memo_viewpoints_stakeholders_concerns::*;

    private import memo_core_common::*;
    viewpoint contextViewpoint : MemoViewpoint {
        @MemoIdentity { :>> providedId = "VP-CTX"; :>> label = "ContextViewpoint"; }
        doc /* Default viewpoint derived from the context layer to communicate who interacts with the device, under which use conditions, and where trust or safety boundaries exist. */
        @MemoIdentity { :>> shortDescription = "Shows actors, use context, and system boundary."; }
        attribute :>> purpose = "Communicate operational context and boundaries.";
        ref :>> memoStakeholders = (systemArchitect);
        attribute :>> stage = WorkflowStageKind::context;
        attribute :>> abstractionLevel = "system";
        attribute :>> outputKind = (ViewOutputKind::diagram);
        attribute :>> presentationKind = (PresentationKind::blockDiagram);
        ref :>> framedConcerns = (safetyConcern, interoperabilityConcern);
        attribute :>> explorerLane = "architecture";
        attribute :>> explorerOrder = 0;
        // UseEnvironment (IEC 62366-1 3.20) is what the device sits inside —
        // facility, procedure area, ambient conditions. A context view that
        // cannot show it is missing half of "where is this used".
        // InteractsInContext is the context relation: a context view draws it
        // and nothing else, so general-purpose model edges cannot leak into the
        // boundary picture. Projects derive their own verbs from it and are
        // picked up through the specialization closure. The three older
        // relations remain for models authored before it existed.
        attribute :>> userExtensible = true;
    }
}
