package memo_viewpoints_ui_layout_ui_layout_viewpoint {
    private import ScalarValues::*;

    private import memo_viewpoints_definitions::*;
    private import memo_core_enumerations::*;
    private import memo_viewpoints_stakeholders_concerns::*;

    private import memo_core_common::*;
    viewpoint uiLayoutViewpoint : MemoViewpoint {
        @MemoIdentity { :>> providedId = "VP-UIL"; :>> label = "UILayoutViewpoint"; }
        doc /* Frames the user interface spatially: a captured rendering of a screen, and the UIElement tree laid out over it by each element's bounds. Supports IEC 62366-1 use-related design review and the UI description in the software design specification, by making 'which control is this, and what does it do' answerable from the picture. There is one tree, not two — the elements carrying the geometry are the same elements carrying the requirements, functions, use errors, and risk controls. */
        @MemoIdentity { :>> shortDescription = "Shows screen captures with the UI element tree laid out over them."; }
        attribute :>> purpose = "Review the interface as the user sees it, with every functional area backed by a design record.";
        ref :>> memoStakeholders = (usabilityEngineer, softwareArchitect, safetyEngineer);
        attribute :>> stage = WorkflowStageKind::architecture;
        attribute :>> abstractionLevel = "implementation";
        attribute :>> outputKind = (ViewOutputKind::diagram, ViewOutputKind::documentSection);
        attribute :>> presentationKind = (PresentationKind::screenLayout);
        ref :>> framedConcerns = (usabilityConcern, safetyConcern);
        attribute :>> explorerLane = "architecture";
        attribute :>> explorerOrder = 4;
        attribute :>> defaultViewKind = DiagramViewKind::geometry;
        attribute :>> userExtensible = true;
    }
}
