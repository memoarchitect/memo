package memo_viewpoints_functional_functional_viewpoint {
    private import ScalarValues::*;

    private import memo_viewpoints_definitions::*;
    private import memo_core_enumerations::*;
    private import memo_viewpoints_stakeholders_concerns::*;

    private import memo_core_common::*;
    viewpoint functionalViewpoint : MemoViewpoint {
        @MemoIdentity { :>> providedId = "VP-FUNC"; :>> label = "FunctionalViewpoint"; }
        doc /* Default viewpoint derived from the functions layer for what the system does, independent of how it is structured — function trees, function allocation, and behavior triggers. */
        @MemoIdentity { :>> shortDescription = "Shows system functions, their decomposition, and allocation."; }
        attribute :>> purpose = "Describe the system's functional decomposition and behavior.";
        ref :>> memoStakeholders = (systemArchitect);
        attribute :>> stage = WorkflowStageKind::architecture;
        attribute :>> abstractionLevel = "functional";
        attribute :>> outputKind = (ViewOutputKind::diagram);
        attribute :>> presentationKind = (PresentationKind::activityDiagram);
        ref :>> framedConcerns = (safetyConcern, performanceConcern);
        attribute :>> explorerLane = "architecture";
        attribute :>> explorerOrder = 2;
        attribute :>> userExtensible = true;
    }
}
