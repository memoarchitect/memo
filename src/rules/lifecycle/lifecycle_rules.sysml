// Lifecycle ordering requires modeled execution timestamps or revision events.
// MEMO currently carries neither on the affected architecture elements, so this
// package declares no consistency constraint: stage guidance is reported by the
// methodology workflow instead of presenting an unevaluable rule as assurance.
package memo_rules_lifecycle {
}
