// Ontology conformance invariants. Same native pattern as memo_rules_closure:
// `constraint def` bodies with declarative rule metadata
// (`predicateExpression`) evaluated by the external constraint engine.
// Structural invariants (endpoint existence, cycle freedom) are expressed over
// the typed relations — typed references make them checkable.
//
// Operational levels (CR-ONT-093..103). A use case and a workflow are each
// declared at a level by their type: `ClinicalUseCase` and `ClinicalWorkflow`
// are level 1 (clinical, no product, no number), `SystemUseCase` and
// `SystemWorkflow` level 2 (one variant of a platform, which carries every
// number). 093 keeps a use case's type and subject in agreement, 103 a
// workflow's type and the use case it `realizesUseCase`. The level of a step is
// the type of the workflow it sits in, reached from the step by `composes` (a
// step nested in a scenario) or through the scenario that `performs` it (a step
// declared once and used in several); a step outside any workflow has no level
// and is judged by no level rule. Each rule reads a type and the `performs` and
// `realizes` edges the builder already produces. Rule 101, that every variant
// of a `TradeStudy` refines every step compared, reads the study's `hasSubject`
// edges: its subject is the alternatives it analyses. The one-currency rule
// (098) counts the project's `CurrencyUnit` declarations: a unit declared at
// package level is built as a model element, as ISQ and SI declare theirs.
package memo_rules_ontology {
    private import ScalarValues::*;

    private import memo_core_consistency_rules::*;
    private import memo_core_enumerations::*;

    private import memo_core_common::*;
    private import memo_artifacts_standards_traceability::EnforcesClause;
    private import memo_artifacts_standards_iec_62366_1::*;
    private import memo_artifacts_standards_iso_13485::*;
    // ─── Structure ───────────────────────────────────────────────────────

    constraint def ContainmentAcyclicRule :> MemoConsistencyRule {
        @MemoIdentity { :>> providedId = "CR-ONT-001"; }
        attribute tailoring = RuleTailoringKind::invariant;
        attribute domain = RuleDomainKind::modelling;
        attribute obligation = RuleObligationKind::recommended;
        attribute appliesTo = "Model";
        attribute severity = RuleSeverityKind::error;
        attribute rationaleText = "Containment/composition relations (Composes) must form no cycles.";
        attribute predicateExpression = "acyclic(composes)";
        constraint { true }
    }
    constraint def ModelDeclaresSystemRule :> MemoConsistencyRule {
        @MemoIdentity { :>> providedId = "CR-ONT-084"; }
        // Tailorable, not an invariant: a library or a model that only extends another has no
        // system of its own, and its method says so with a rationale.
        attribute tailoring = RuleTailoringKind::methodology;
        attribute domain = RuleDomainKind::modelling;
        attribute obligation = RuleObligationKind::recommended;
        attribute appliesTo = "Model";
        attribute severity = RuleSeverityKind::error;
        attribute rationaleText = "A model declares at least one System (a part def that specializes System). A workspace is the closure of what is linked to the definition of a System, so a model with only a usage typed by System, or none, has no workspace: nothing can be scoped, and every element is Unassigned.";
        attribute predicateExpression = "allOfKind('System')->exists(isDefinition == 'true')";
        constraint { true }
    }
    // ─── Use case scope ─────────────────────────────────────────
    //
    // The level of a use case is its declared type (`ClinicalUseCase`, `SystemUseCase`), and
    // CR-ONT-093 keeps it in agreement with the subject (`hasSubject`). Rule 085 reads the subject
    // for what it says about composition, not for the level. A use case with no subject
    // is judged by no rule on the subject.

    constraint def SosUseCaseIncludesSystemUseCaseRule :> MemoConsistencyRule {
        @MemoIdentity { :>> providedId = "CR-ONT-085"; }
        attribute tailoring = RuleTailoringKind::methodology;
        attribute domain = RuleDomainKind::modelling;
        attribute obligation = RuleObligationKind::recommended;
        attribute appliesTo = "UseCase";
        attribute severity = RuleSeverityKind::warning;
        attribute rationaleText = "A use case whose subject is a system of systems is made of what its systems do: it includes at least one use case whose subject is a system.";
        attribute predicateExpression = "not(downstream(hasSubject)->exists(conformsTo(SystemOfSystems))) or downstream(includesStep)->exists(downstream(hasSubject)->exists(conformsTo(System)))";
        constraint { true }
    }
    // ─── Release selections ────────────────────────────────────
    //
    // A release record selects features (`#SelectsFeature`), and through them the variants that realize
    // them (`#RealizesFeature`, variant to feature). The rules read a record's selection by navigation;
    // `selectRelease` (memo-tools `model/variability.ts`) is the same join in code and a test holds the
    // two equal. `upstream` / `downstream` are transitive and directed; the bare relation name is one
    // hop in both directions, which is what the symmetric `excludesFeature` needs (a transitive reading
    // would make A and C exclusive because each excludes B).

    constraint def ReleaseSelectsProposedVariantRule :> MemoConsistencyRule {
        @MemoIdentity { :>> providedId = "CR-ONT-088"; }
        attribute tailoring = RuleTailoringKind::methodology;
        attribute domain = RuleDomainKind::modelling;
        attribute obligation = RuleObligationKind::recommended;
        attribute appliesTo = "ReleaseRecord";
        attribute severity = RuleSeverityKind::error;
        attribute rationaleText = "An approved or released record contains what it selects. A feature whose variant is still proposed has no approved design behind it, so a record that has passed approval cannot select it. A record with no status, or one still being drafted, is not judged.";
        attribute predicateExpression = "not(attributes.status == 'ElementStatusKind::approved' or attributes.status == 'ElementStatusKind::released') or downstream(selectsFeature)->forAll(upstream(realizesFeature)->forAll(attributes.status != 'ElementStatusKind::proposed'))";
        constraint { true }
    }
    constraint def ReleaseSelectionConsistentRule :> MemoConsistencyRule {
        @MemoIdentity { :>> providedId = "CR-ONT-089"; }
        // An invariant: requires and excludes are the family's own declarations, and a selection that
        // breaks them contradicts the model, whatever the record's status.
        attribute tailoring = RuleTailoringKind::invariant;
        attribute domain = RuleDomainKind::modelling;
        attribute obligation = RuleObligationKind::recommended;
        attribute appliesTo = "ReleaseRecord";
        attribute severity = RuleSeverityKind::error;
        attribute rationaleText = "A record selects a set of features that satisfies the family's rules: every feature a selected feature requires is selected too, and no two selected features exclude each other.";
        attribute predicateExpression = "downstream(selectsFeature)->forAll(downstream(requiresFeature)->forAll(upstream(selectsFeature)->exists(id == subject.id)) and excludesFeature->forAll(upstream(selectsFeature)->forAll(id != subject.id)))";
        constraint { true }
    }
    // Every variation point of the item a record is a release of is resolved to ONE variant, and no
    // variation point anywhere has two. Two halves, one rule:
    //   at most one  -- any record, any status: a record that selects the features of two variants
    //                   of one point describes no product. Needs no item.
    //   exactly one  -- an approved or released record that is `#ReleaseOf` an item: each variation
    //                   point the item owns (`composes`, transitive, so an SoS record judges the
    //                   points of the SoS and each system record those of its own system; ownership
    //                   does not cross typing) has one selected variant. A draft is allowed to be
    //                   unfinished, as in CR-ONT-088.
    // Not asked of the exactly-one half: a point none of whose variants realizes a feature (a
    // release can neither select nor drop its variants, so it cannot resolve it), a point owned by
    // a variant the record does not select (it is not in the product), and a record with no
    // `#ReleaseOf` (no item to judge, a limit; the at-most-one half still runs).
    // `selectRelease` (memo-tools `model/variability.ts`) is the same definition in code and a test
    // holds the two equal. Limit: `variant` is followed transitively, so a variant that is itself a
    // variation point counts its own variants against its parent's.
    constraint def ReleaseSelectsOneVariantRule :> MemoConsistencyRule {
        @MemoIdentity { :>> providedId = "CR-ONT-090"; }
        attribute tailoring = RuleTailoringKind::invariant;
        attribute domain = RuleDomainKind::modelling;
        attribute obligation = RuleObligationKind::recommended;
        attribute appliesTo = "ReleaseRecord";
        attribute severity = RuleSeverityKind::error;
        attribute rationaleText = "A variation point is one choice. A record that selects the features of two of its variants builds both, and an approved or released record of an item that selects none of a variation point's variants builds neither, so it describes no single product.";
        attribute predicateExpression = "downstream(selectsFeature)->forAll(upstream(realizesFeature)->forAll(upstream(variant)->forAll(downstream(variant)->select(downstream(realizesFeature)->exists(upstream(selectsFeature)->exists(id == subject.id)))->size() <= 1))) and (not(attributes.status == 'ElementStatusKind::approved' or attributes.status == 'ElementStatusKind::released') or downstream(releaseOf)->forAll(downstream(composes)->select(attributes.isVariation == 'true')->forAll(not(downstream(variant)->exists(downstream(realizesFeature)->notEmpty())) or upstream(composes)->exists(upstream(variant)->notEmpty() and downstream(realizesFeature)->notEmpty() and not(downstream(realizesFeature)->exists(upstream(selectsFeature)->exists(id == subject.id)))) or downstream(variant)->select(downstream(realizesFeature)->exists(upstream(selectsFeature)->exists(id == subject.id)))->size() == 1)))";
        constraint { true }
    }
    constraint def NestedPartConnectedRule :> MemoConsistencyRule {
        @MemoIdentity { :>> providedId = "AR-IBD-001"; }
        attribute tailoring = RuleTailoringKind::invariant;
        attribute domain = RuleDomainKind::modelling;
        attribute obligation = RuleObligationKind::recommended;
        // Internal-block connectivity is a structural-architecture concern, so
        // the subject is the structural component — not every MemoPart. UI
        // elements, captured evidence, and review comments nest in compositions
        // without ever bearing a connector, and judging them produced warnings
        // no modeller could act on. The engine reads this value; narrowing or
        // widening the rule happens here, not in TypeScript.
        attribute appliesTo = "LogicalComponent";
        attribute evaluator = "architecture";
        attribute severity = RuleSeverityKind::warning;
        attribute rationaleText = "A structural part nested inside another part should expose at least one modeled interface connector. Passive or intentionally isolated parts may retain this warning with an explicit modelling rationale.";
        attribute predicateExpression = "hasConnectorInComposition";
        // Graph-aware structural rule, evaluated by Memo Architect's rule
        // engine: it lifts port endpoints to their owning part, ignores
        // composition/trace/deployment links, and includes a connected child's
        // containing assemblies. The generic KerML expression evaluator cannot
        // represent that transitive containment query.
        constraint { true }
    }

    // ─── Direction is written on the ports, and an exchange has to agree with them ──
    //
    // A port says `in` or `out` (or `inout`), and a `~` conjugates it. That is
    // the only place direction is written. These two rules check the exchange
    // against its ports, so a contradiction cannot be written. Both judge only
    // ends that are ports with a stated direction; a port that says none is not
    // judged.
    constraint def BindingEndsAgreeInDirectionRule :> MemoConsistencyRule {
        @MemoIdentity { :>> providedId = "AR-EXCH-001"; }
        attribute tailoring = RuleTailoringKind::invariant;
        attribute domain = RuleDomainKind::modelling;
        attribute obligation = RuleObligationKind::recommended;
        attribute appliesTo = "MemoPort";
        attribute evaluator = "architecture";
        attribute severity = RuleSeverityKind::error;
        attribute rationaleText = "A binding makes its two ports one connection point, so they have the direction between them: a boundary port bound to a port of a nested part passes the same direction through. A binding of an in port to an out port joins things that cannot be the same point.";
        attribute predicateExpression = "bindEndsAgreeInDirection";
        // The generic expression evaluator reads a port's attributes, not its stated direction and
        // conjugation, so a function computes the predicate (as for AR-IBD-001).
        constraint { true }
    }
    constraint def ExchangeLeavesOutEntersInRule :> MemoConsistencyRule {
        @MemoIdentity { :>> providedId = "AR-EXCH-002"; }
        attribute tailoring = RuleTailoringKind::invariant;
        attribute domain = RuleDomainKind::modelling;
        attribute obligation = RuleObligationKind::recommended;
        attribute appliesTo = "MemoPort";
        attribute evaluator = "architecture";
        attribute severity = RuleSeverityKind::error;
        attribute rationaleText = "An interface or a flow between two ports carries its content from the one to the other, so it leaves a port that sends (out or inout) and enters one that receives (in or inout). An exchange that leaves an in port or enters an out port contradicts the ports it joins.";
        attribute predicateExpression = "exchangeLeavesOutEntersIn";
        constraint { true }
    }
    // ─── Deployment and realization ──────────────────────────────────────

    constraint def RuntimeTracesToModuleRule :> MemoConsistencyRule {
        @MemoIdentity { :>> providedId = "CR-ONT-011"; }
        attribute tailoring = RuleTailoringKind::invariant;
        attribute domain = RuleDomainKind::modelling;
        attribute obligation = RuleObligationKind::recommended;
        attribute appliesTo = "SoftwareComponent";
        attribute severity = RuleSeverityKind::warning;
        attribute rationaleText = "Every runtime component must trace to a module-view definition (Realizes).";
        attribute predicateExpression = "realizes->size() >= 1";
        constraint { true }
    }
    // The ontology declares one relation for a logical component and what realizes it:
    // `RealizedBy` in memo_architecture_realization_deployment. The general `#refinement`
    // stays for every other realization, so this rule keeps the logical case to one spelling.
    constraint def LogicalRealizedByAllocationRule :> MemoConsistencyRule {
        @MemoIdentity { :>> providedId = "CR-ONT-105"; }
        attribute tailoring = RuleTailoringKind::invariant;
        attribute domain = RuleDomainKind::modelling;
        attribute obligation = RuleObligationKind::recommended;
        attribute appliesTo = "LogicalComponent";
        attribute severity = RuleSeverityKind::error;
        attribute rationaleText = "A logical component is allocated to the hardware or software that realizes it with RealizedBy, the logical component first. A #refinement dependency from an implementation element to a logical component says the same thing a second way, and the workspace places its ends differently.";
        attribute predicateExpression = "upstream(realizes)->forAll(conformsTo(LogicalComponent))";
        constraint { true }
    }
    constraint def PatientContactCharacterizedRule :> MemoConsistencyRule {
        @MemoIdentity { :>> providedId = "CR-ONT-032"; }
        attribute tailoring = RuleTailoringKind::assurance;
        attribute domain = RuleDomainKind::medicalDevice;
        attribute obligation = RuleObligationKind::recommended;
        attribute appliesTo = "PhysicalComponent";
        attribute severity = RuleSeverityKind::error;
        attribute rationaleText = "Patient-contact components must identify contact nature and duration (ISO 10993-1).";
        attribute predicateExpression = "patientContact == false or (contactNature != '' and contactDuration != '')";
        constraint { true }
    }

    // ─── Assurance coverage ──────────────────────────────────────────────

    constraint def SafetyCriticalFunctionVerifiedRule :> MemoConsistencyRule {
        @MemoIdentity { :>> providedId = "CR-ONT-040"; }
        attribute tailoring = RuleTailoringKind::assurance;
        attribute domain = RuleDomainKind::medicalDevice;
        attribute obligation = RuleObligationKind::required;
        // To confirm: inferred from the clause scope; confirm.
        attribute appliesTo = "MemoFunction";
        attribute severity = RuleSeverityKind::error;
        attribute rationaleText = "Safety-critical functions (criticality high or catastrophic) must trace to at least one verification case.";
        attribute predicateExpression = "not(criticality == 'high' or criticality == 'catastrophic') or verifiedBy->size() >= 1";
        constraint { true }
    }
    #EnforcesClause dependency from SafetyCriticalFunctionVerifiedRule to iso13485::iso13485Clause7::iso13485Clause7_3::iso13485Clause7_3_6;
    // A flow's step is its own position of a function (`action step :> fn;`), and evidence is scoped to
    // the position: a test of the function, or of another step, does not count for it. So a step whose
    // function is safety-critical needs a verification case of its own. The step reaches its function
    // through the `subsets` edge.
    constraint def SafetyCriticalStepVerifiedRule :> MemoConsistencyRule {
        @MemoIdentity { :>> providedId = "CR-ONT-091"; }
        attribute tailoring = RuleTailoringKind::assurance;
        attribute domain = RuleDomainKind::medicalDevice;
        attribute obligation = RuleObligationKind::recommended;
        attribute appliesTo = "ActionUsage";
        attribute severity = RuleSeverityKind::warning;
        attribute rationaleText = "A step of a flow whose function is safety-critical (criticality high or catastrophic) must trace to a verification case of its own; a test of the function or of another step does not cover it.";
        attribute predicateExpression = "not(downstream(subsets)->exists(criticality == 'high' or criticality == 'catastrophic')) or verifiedBy->size() >= 1";
        constraint { true }
    }
    #EnforcesClause dependency from SafetyCriticalStepVerifiedRule to iso13485::iso13485Clause7::iso13485Clause7_3::iso13485Clause7_3_6;
    constraint def CriticalTaskValidatedRule :> MemoConsistencyRule {
        @MemoIdentity { :>> providedId = "CR-ONT-041"; }
        attribute tailoring = RuleTailoringKind::assurance;
        attribute domain = RuleDomainKind::medicalDevice;
        attribute obligation = RuleObligationKind::required;
        // To confirm: inferred from the clause scope; the FDA human-factors
        // guidance it also cites is not in the library yet. The criticality
        // test lives in the predicate alone, so catastrophic tasks are in
        // scope. `testedByUsability` is the relation the human-factors package
        // declares for exactly this link.
        attribute appliesTo = "OperativeAction";
        attribute severity = RuleSeverityKind::error;
        attribute rationaleText = "Critical tasks (criticality high or catastrophic) must trace to usability validation (FDA HF guidance; IEC 62366-1 summative evaluation).";
        attribute predicateExpression = "not(criticality == 'high' or criticality == 'catastrophic') or testedByUsability->size() >= 1 or validates->size() >= 1";
        constraint { true }
    }
    #EnforcesClause dependency from CriticalTaskValidatedRule to iec62366_1::iec62366_1Clause5::iec62366_1Clause5_9;
    constraint def UseErrorTracesToHazardRule :> MemoConsistencyRule {
        @MemoIdentity { :>> providedId = "CR-ONT-042"; }
        attribute tailoring = RuleTailoringKind::assurance;
        attribute domain = RuleDomainKind::medicalDevice;
        attribute obligation = RuleObligationKind::required;
        // To confirm: inferred from the clause scope; confirm.
        attribute appliesTo = "UseError";
        attribute severity = RuleSeverityKind::warning;
        attribute rationaleText = "Safety-relevant use errors (severity serious or worse) must trace to a hazard.";
        attribute predicateExpression = "not(severity == 'serious' or severity == 'critical' or severity == 'catastrophic') or causes->size() >= 1 or tracesRisk->size() >= 1";
        constraint { true }
    }
    #EnforcesClause dependency from UseErrorTracesToHazardRule to iec62366_1::iec62366_1Clause5::iec62366_1Clause5_3;
    // ─── Relation end conformance ─────────────────────────────
    //
    // These rules carry the constraints on `connection def` ends that a type
    // cannot state: KerML forbids a port or a behaviour from specializing a
    // part-based type, so a `MemoPart`-typed end would force every endpoint to
    // be a part. See the note on metaclass-neutral ends in
    // memo_core_relationships.
    //
    // Each rule states its end's constraint, in the one vocabulary that spans
    // the metaclasses:
    //
    // * `conformsTo(Base)` — SysML specialization against a MEMO base. This
    // works within a metaclass. * `construct == 'action' | 'port' | 'state' |
    // …` — the SysML METACLASS. No MEMO base can say this, because the bases
    // are per-metaclass by construction; a type-based end could only ever admit
    // one of them.
    //
    // Subject scope is `Model`, following CR-ONT-001: a statement about the ends
    // of a relation quantifies over its LINKS, not over elements of one kind, so
    // no per-element subject can reach it. The cost is that a violation names
    // the rule and not the offending link; the rationale text names the relation
    // and the admissible types so the report is still actionable.

    constraint def SatisfiedBySourceKindRule :> MemoConsistencyRule {
        @MemoIdentity { :>> providedId = "CR-ONT-060"; }
        attribute tailoring = RuleTailoringKind::invariant;
        attribute domain = RuleDomainKind::modelling;
        attribute obligation = RuleObligationKind::recommended;
        attribute appliesTo = "Model";
        attribute severity = RuleSeverityKind::error;
        attribute rationaleText = "Only a requirement or a need is satisfied by something. The source end of SatisfiedBy must conform to MemoRequirementElement.";
        attribute predicateExpression = "sourcesOf(satisfiedBy)->forAll(conformsTo(MemoRequirementElement))";
        constraint { true }
    }
    constraint def SatisfiedByTargetKindRule :> MemoConsistencyRule {
        @MemoIdentity { :>> providedId = "CR-ONT-061"; }
        attribute tailoring = RuleTailoringKind::invariant;
        attribute domain = RuleDomainKind::modelling;
        attribute obligation = RuleObligationKind::recommended;
        attribute appliesTo = "Model";
        attribute severity = RuleSeverityKind::error;
        attribute rationaleText = "A requirement is satisfied by a designed part, a behaviour, or a port. Never by another requirement or by a document.";
        attribute predicateExpression = "targetsOf(satisfiedBy)->forAll(conformsTo(MemoPart) or construct == 'action' or construct == 'port')";
        constraint { true }
    }
    constraint def VerifiedByTargetKindRule :> MemoConsistencyRule {
        @MemoIdentity { :>> providedId = "CR-ONT-062"; }
        attribute tailoring = RuleTailoringKind::invariant;
        attribute domain = RuleDomainKind::modelling;
        attribute obligation = RuleObligationKind::recommended;
        attribute appliesTo = "Model";
        attribute severity = RuleSeverityKind::error;
        attribute rationaleText = "A verification case verifies a requirement, a risk control, an architecture element, a behaviour, or a port — something a test can be run against. Not a view, not an evidence record.";
        attribute predicateExpression = "sourcesOf(verifiedBy)->forAll(conformsTo(MemoPart) or construct == 'requirement' or construct == 'action' or construct == 'port')";
        constraint { true }
    }
    constraint def AllocatedToSourceKindRule :> MemoConsistencyRule {
        @MemoIdentity { :>> providedId = "CR-ONT-063"; }
        attribute tailoring = RuleTailoringKind::invariant;
        attribute domain = RuleDomainKind::modelling;
        attribute obligation = RuleObligationKind::recommended;
        attribute appliesTo = "Model";
        attribute severity = RuleSeverityKind::error;
        attribute rationaleText = "Allocation runs from a function or a behaviour to where it runs. The source end of AllocatedTo is a part, an action, or a functional exchange (allocated to a component exchange, as ARCADIA allocates one).";
        attribute predicateExpression = "sourcesOf(allocatedTo)->forAll(conformsTo(MemoPart) or construct == 'action' or conformsTo(FunctionalExchange))";
        constraint { true }
    }
    constraint def AllocatedToTargetKindRule :> MemoConsistencyRule {
        @MemoIdentity { :>> providedId = "CR-ONT-064"; }
        attribute tailoring = RuleTailoringKind::invariant;
        attribute domain = RuleDomainKind::modelling;
        attribute obligation = RuleObligationKind::recommended;
        attribute appliesTo = "Model";
        attribute severity = RuleSeverityKind::error;
        attribute rationaleText = "A function is allocated to a part — including a system or actor — as ARCADIA System Analysis requires; a functional exchange is allocated to a component exchange.";
        attribute predicateExpression = "targetsOf(allocatedTo)->forAll(conformsTo(MemoPart) or conformsTo(ComponentExchange))";
        constraint { true }
    }
    constraint def ComposesParentKindRule :> MemoConsistencyRule {
        @MemoIdentity { :>> providedId = "CR-ONT-065"; }
        attribute tailoring = RuleTailoringKind::invariant;
        attribute domain = RuleDomainKind::modelling;
        attribute obligation = RuleObligationKind::recommended;
        attribute appliesTo = "Model";
        attribute severity = RuleSeverityKind::error;
        attribute rationaleText = "A whole in a decomposition is a part, a behaviour, or a state machine. A requirement does not compose anything.";
        attribute predicateExpression = "sourcesOf(composes)->forAll(conformsTo(MemoPart) or construct == 'action' or construct == 'state')";
        constraint { true }
    }
    constraint def ComposesChildKindRule :> MemoConsistencyRule {
        @MemoIdentity { :>> providedId = "CR-ONT-066"; }
        attribute tailoring = RuleTailoringKind::invariant;
        attribute domain = RuleDomainKind::modelling;
        attribute obligation = RuleObligationKind::recommended;
        attribute appliesTo = "Model";
        attribute severity = RuleSeverityKind::error;
        attribute rationaleText = "A part in a decomposition is a part, a behaviour, a state, or a port — a component owns its ports, and a workflow owns its steps.";
        attribute predicateExpression = "targetsOf(composes)->forAll(conformsTo(MemoPart) or construct == 'action' or construct == 'state' or construct == 'port')";
        constraint { true }
    }
    constraint def PrecedesEndKindRule :> MemoConsistencyRule {
        @MemoIdentity { :>> providedId = "CR-ONT-067"; }
        attribute tailoring = RuleTailoringKind::invariant;
        attribute domain = RuleDomainKind::modelling;
        attribute obligation = RuleObligationKind::recommended;
        attribute appliesTo = "Model";
        attribute severity = RuleSeverityKind::error;
        attribute rationaleText = "Precedence orders things that happen: parts or behaviours, at both ends.";
        attribute predicateExpression = "sourcesOf(precedes)->forAll(conformsTo(MemoPart) or construct == 'action') and targetsOf(precedes)->forAll(conformsTo(MemoPart) or construct == 'action')";
        constraint { true }
    }
    constraint def PerformsPerformerKindRule :> MemoConsistencyRule {
        @MemoIdentity { :>> providedId = "CR-ONT-068"; }
        attribute tailoring = RuleTailoringKind::invariant;
        attribute domain = RuleDomainKind::modelling;
        attribute obligation = RuleObligationKind::recommended;
        attribute appliesTo = "Model";
        attribute severity = RuleSeverityKind::error;
        attribute rationaleText = "A performer is an operational entity, an actor, or a system action — a part or a behaviour. The end's own documentation said 'or system action' while its MemoPart type forbade one.";
        attribute predicateExpression = "sourcesOf(performs)->forAll(conformsTo(MemoPart) or construct == 'action' or construct == 'verification')";
        constraint { true }
    }
    constraint def BindsToInterfaceEndKindRule :> MemoConsistencyRule {
        @MemoIdentity { :>> providedId = "CR-ONT-070"; }
        attribute tailoring = RuleTailoringKind::invariant;
        attribute domain = RuleDomainKind::modelling;
        attribute obligation = RuleObligationKind::recommended;
        attribute appliesTo = "Model";
        attribute severity = RuleSeverityKind::error;
        attribute rationaleText = "A port binds to an interface. The bound end is an interface definition, which the former InterfaceElement-typed end could not hold at all — Interface specializes MemoInterface, an interface def, not a part.";
        attribute predicateExpression = "sourcesOf(bindsToInterface)->forAll(conformsTo(InterfaceElement) or construct == 'port') and targetsOf(bindsToInterface)->forAll(conformsTo(InterfaceElement) or construct == 'interface' or construct == 'port')";
        constraint { true }
    }
    constraint def CrossesTrustBoundaryEndKindRule :> MemoConsistencyRule {
        @MemoIdentity { :>> providedId = "CR-ONT-071"; }
        attribute tailoring = RuleTailoringKind::invariant;
        attribute domain = RuleDomainKind::modelling;
        attribute obligation = RuleObligationKind::recommended;
        attribute appliesTo = "Model";
        attribute severity = RuleSeverityKind::error;
        attribute rationaleText = "A boundary is a boundary element or a port; what crosses it is an asset, an item, or an exchange: an interface or a flow.";
        attribute predicateExpression = "sourcesOf(crossesTrustBoundary)->forAll(conformsTo(InterfaceElement) or construct == 'port') and targetsOf(crossesTrustBoundary)->forAll(conformsTo(MemoPart) or construct == 'item' or construct == 'interface' or construct == 'flow')";
        constraint { true }
    }

    // A ComponentExchange is an interface, so its ends are the ports it
    // connects, and `sourceEnd` / `targetEnd` are those elements. The compiler
    // does not check this: a compiler accepts a part at an interface end even
    // when the definition types the ends.
    constraint def ComponentExchangeSourceEndpointKindRule :> MemoConsistencyRule {
        @MemoIdentity { :>> providedId = "CR-ONT-072"; }
        attribute tailoring = RuleTailoringKind::invariant;
        attribute domain = RuleDomainKind::modelling;
        attribute obligation = RuleObligationKind::recommended;
        attribute appliesTo = "ComponentExchange";
        attribute severity = RuleSeverityKind::error;
        attribute rationaleText = "A component exchange starts at a port. An exchange that starts at a component names no boundary, so nothing says where on the component it enters or leaves, and no port can carry its item type or direction.";
        attribute predicateExpression = "sourceEnd->size() == 1 and sourceEnd->forAll(construct == 'port')";
        constraint { true }
    }
    constraint def ComponentExchangeTargetEndpointKindRule :> MemoConsistencyRule {
        @MemoIdentity { :>> providedId = "CR-ONT-073"; }
        attribute tailoring = RuleTailoringKind::invariant;
        attribute domain = RuleDomainKind::modelling;
        attribute obligation = RuleObligationKind::recommended;
        attribute appliesTo = "ComponentExchange";
        attribute severity = RuleSeverityKind::error;
        attribute rationaleText = "A component exchange ends at a port, on the same grounds as CR-ONT-072.";
        attribute predicateExpression = "targetEnd->size() == 1 and targetEnd->forAll(construct == 'port')";
        constraint { true }
    }

    // ─── The functional chain ────────────────────────────────────────────
    //
    // What makes ComponentFunction a definition of its own rather than an enum
    // member on SystemFunction. An enum value cannot change a multiplicity, and
    // "answerable to exactly one component" is the whole content of the concept.

    constraint def ComponentFunctionAllocatedRule :> MemoConsistencyRule {
        @MemoIdentity { :>> providedId = "CR-ONT-074"; }
        attribute tailoring = RuleTailoringKind::invariant;
        attribute domain = RuleDomainKind::modelling;
        attribute obligation = RuleObligationKind::recommended;
        attribute appliesTo = "ComponentFunction";
        attribute severity = RuleSeverityKind::error;
        attribute rationaleText = "A component function is the responsibility of exactly one component, and AllocatedTo is what names it. A component function allocated nowhere is a responsibility nobody has accepted; one allocated twice is a responsibility nobody owns. A system-level responsibility with no single owner is a SystemFunction, which allows that. A definition is a type and is not allocated; its usages are.";
        attribute predicateExpression = "isDefinition == 'true' or allocatedTo->size() == 1";
        constraint { true }
    }
    constraint def FunctionDecomposesIntoFunctionsRule :> MemoConsistencyRule {
        @MemoIdentity { :>> providedId = "CR-ONT-075"; }
        attribute tailoring = RuleTailoringKind::invariant;
        attribute domain = RuleDomainKind::modelling;
        attribute obligation = RuleObligationKind::recommended;
        attribute appliesTo = "MemoFunction";
        attribute severity = RuleSeverityKind::error;
        attribute rationaleText = "The functional chain decomposes functions into functions. A function composed of a component, or owned by one, is confusing allocation with decomposition — the component is named by AllocatedTo, never by Composes. A functional flow is a behaviour, not a component: a function step inside one is decomposition.";
        attribute predicateExpression = "composes->forAll(conformsTo(MemoFunction) or conformsTo(FunctionalFlow) or kind == 'ForkNode' or kind == 'JoinNode' or kind == 'DecisionNode' or kind == 'MergeNode')";
        constraint { true }
    }

    // ── Containment stays inside one family ─────────────────────────────
    //
    // CR-ONT-075 above is this rule for functions; these are the same shape for
    // the other families. The invariant is FAMILY homogeneity, not type
    // homogeneity: a System containing a Subsystem containing a LogicalComponent
    // is correct decomposition even though all three types differ, and measured
    // 2026-08-18 only 1 of 68 containment edges had identical types at both
    // ends — a same-type rule would have rejected 98.5% of the corpus, the
    // ontology's own templates included.
    //
    // What they catch is containment CROSSING a family: a logical component
    // "containing" a software module is realization, and a hardware assembly
    // "containing" a function is allocation. Both have their own relation, and
    // writing them as containment loses the distinction.
    //
    // They read the `composes` edge, which the builder synthesizes from native
    // nesting. They read it DOWNSTREAM: a bare relation name navigates both
    // ways, so `composes` alone would reach the subject's own parent and report
    // one cross-family nesting twice. `downstream` is transitive, so the rule
    // reads as "the subtree stays in the family".
    //
    // Ports are exempt. A port is a boundary FEATURE of its owner, not a member
    // of its owner's family, and any element may carry one whatever family it
    // is in — CR-ONT-065/066 already govern what may sit at a containment end.
    // Without the exemption these rules reject `SoftwareModule composes
    // PhysicalPort`, which those rules accept, and the ontology contradicts
    // itself about a single edge.
    constraint def SoftwareContainsSoftwareRule :> MemoConsistencyRule {
        @MemoIdentity { :>> providedId = "CR-ONT-077"; }
        attribute tailoring = RuleTailoringKind::invariant;
        attribute domain = RuleDomainKind::modelling;
        attribute obligation = RuleObligationKind::recommended;
        attribute appliesTo = "SoftwareElement";
        attribute severity = RuleSeverityKind::error;
        attribute rationaleText = "Software contains software. A software element containing a logical or physical one is realization, not containment — that is a refinement dependency.";
        attribute predicateExpression = "downstream(composes)->forAll(construct == 'port' or construct == 'package' or conformsTo(SoftwareElement))";
        constraint { true }
    }
    constraint def LogicalContainsLogicalRule :> MemoConsistencyRule {
        @MemoIdentity { :>> providedId = "CR-ONT-078"; }
        attribute tailoring = RuleTailoringKind::invariant;
        attribute domain = RuleDomainKind::modelling;
        attribute obligation = RuleObligationKind::recommended;
        attribute appliesTo = "LogicalComponent";
        attribute severity = RuleSeverityKind::error;
        attribute rationaleText = "The logical hierarchy decomposes into logical components. A logical component containing a software module or a physical part is realization — the implementation element refines the logical one, it is not part of it.";
        attribute predicateExpression = "downstream(composes)->forAll(construct == 'port' or construct == 'package' or conformsTo(LogicalComponent))";
        constraint { true }
    }
    constraint def PhysicalContainsPhysicalRule :> MemoConsistencyRule {
        @MemoIdentity { :>> providedId = "CR-ONT-079"; }
        attribute tailoring = RuleTailoringKind::invariant;
        attribute domain = RuleDomainKind::modelling;
        attribute obligation = RuleObligationKind::recommended;
        attribute appliesTo = "PhysicalElement";
        attribute severity = RuleSeverityKind::error;
        attribute rationaleText = "An assembly contains physical things. PhysicalElement is the shared root the family gained for this rule — PhysicalAssembly and PhysicalComponent previously specialized MemoPart separately, which left no type meaning 'a physical thing' to name here.";
        attribute predicateExpression = "downstream(composes)->forAll(construct == 'port' or construct == 'package' or conformsTo(PhysicalElement))";
        constraint { true }
    }

    // An interface is the path between two ports; the flow over it is what
    // moves. This rule asks that a component exchange carries one: a flow
    // whose ends are the exchange's own two ports. The ends are compared as
    // elements (`intersects` matches exact ids), not as names.
    //
    // `assurance`, not `invariant`: whether every interface must declare its
    // transport is a method's call, and a method that models interfaces before
    // their flows may tailor it.
    constraint def ExchangeHasFlowRule :> MemoConsistencyRule {
        @MemoIdentity { :>> providedId = "CR-ONT-076"; }
        attribute tailoring = RuleTailoringKind::assurance;
        attribute domain = RuleDomainKind::modelling;
        attribute obligation = RuleObligationKind::recommended;
        attribute appliesTo = "ComponentExchange";
        attribute severity = RuleSeverityKind::error;
        attribute rationaleText = "A component exchange is the connection between two ports; the flow is what crosses it. An exchange with no flow between its ports declares a path that nothing uses, so its timing and kind describe no transfer.";
        attribute predicateExpression = "linksOf(flow)->exists(sourceEnd->intersects(subject.sourceEnd) and targetEnd->intersects(subject.targetEnd))";
        constraint { true }
    }

    // A functional exchange moves something between two functions. This asks
    // that both ends sit in some behaviour: performed by an action or contained
    // in one. It is weaker than "a scenario walks it", which the model cannot
    // tell apart from a function nested in another function.
    //
    // `warning` and `assurance`: a method that models the exchanges first and
    // the scenarios later tailors it.
    constraint def ExchangeEndsInBehaviourRule :> MemoConsistencyRule {
        @MemoIdentity { :>> providedId = "CR-ONT-104"; }
        attribute tailoring = RuleTailoringKind::assurance;
        attribute domain = RuleDomainKind::modelling;
        attribute obligation = RuleObligationKind::recommended;
        attribute appliesTo = "FunctionalExchange";
        attribute severity = RuleSeverityKind::warning;
        attribute rationaleText = "Both ends of a functional exchange should be in a behaviour. An exchange with an end that no action performs or contains cannot be reached by walking one.";
        attribute predicateExpression = "sourceEnd->forAll(upstream(performs)->exists(construct == 'action') or upstream(composes)->exists(construct == 'action')) and targetEnd->forAll(upstream(performs)->exists(construct == 'action') or upstream(composes)->exists(construct == 'action'))";
        constraint { true }
    }

    // The predicate here named three features that do not exist — `variantKind`,
    // `baseScenario`, `variationPoint` — so it could never fail, and a rule that
    // cannot fail is coverage on paper only. `baseScenario` is the one the
    // scenario def deliberately refused: "a nominal/alternate pair are scenarios
    // of the same workflow, distinguished by scenarioKind — no baseScenario
    // back-ref". The base of an alternate IS the nominal scenario of its
    // workflow, so the rule asks the containment that already expresses it.
    constraint def AlternateScenarioHasBaseRule :> MemoConsistencyRule {
        @MemoIdentity { :>> providedId = "CR-ONT-043"; }
        attribute tailoring = RuleTailoringKind::invariant;
        attribute domain = RuleDomainKind::modelling;
        attribute obligation = RuleObligationKind::recommended;
        attribute appliesTo = "OperativeScenario";
        attribute severity = RuleSeverityKind::error;
        attribute rationaleText = "An alternate scenario is a variation of a nominal path, so it belongs to a workflow that has one. An alternate with no nominal sibling is either a workflow with no happy path or a scenario filed under the wrong parent.";
        // A nominal scenario usually says nothing: `nominal` is the default on
        // the definition, and a default is not written onto every usage. So the
        // sibling test is "not alternate", and `conformsTo` keeps it from being
        // satisfied by an ordinary step of the same workflow.
        //
        // The base may be found three ways, and the workflow sibling is only
        // the first. A use case is what a main scenario and its extensions
        // vary from, so an alternate realizing a use case that a nominal
        // scenario also realizes has its base, whichever workflow holds each
        // (gpca-pump files its alarm responses in a workflow of their own). A
        // scenario with no workflow at all has its package as its parent, so
        // its siblings are the package's other workflow-less scenarios.
        attribute predicateExpression = "not(scenarioKind == 'alternate') or composes.composes->exists(conformsTo(OperativeScenario) and scenarioKind != 'alternate') or downstream(realizes).realizes->exists(conformsTo(OperativeScenario) and scenarioKind != 'alternate') or (upstream(composes)->isEmpty() and allOfKind('OperativeScenario')->exists(package == subject.package and scenarioKind != 'alternate' and upstream(composes)->isEmpty()))";
        constraint { true }
    }

    // ─── Assurance-trace warnings ────────────────────────────────────────
    // A WARNING, not an error: it describes a trace graph that is suspicious
    // rather than invalid, and a regulated model has legitimate exceptions. It
    // reads `upstream` / `downstream` because the bare relation name is
    // bidirectional.
    //
    // A trace is not redundant when one element satisfies both a requirement
    // and one derived from it: a `derive` does not make its source satisfied,
    // and a response-time requirement derived from "select a drug from the
    // library" says nothing about whether the selector lets you select one.

    constraint def DerivationGapRule :> MemoConsistencyRule {
        @MemoIdentity { :>> providedId = "CR-ONT-080"; }
        attribute tailoring = RuleTailoringKind::invariant;
        attribute domain = RuleDomainKind::modelling;
        attribute obligation = RuleObligationKind::recommended;
        attribute appliesTo = "MemoRequirementElement";
        attribute severity = RuleSeverityKind::warning;
        attribute rationaleText = "A requirement that others derive from should itself be justified. If nothing is upstream of it and it is not a stakeholder need, the derivation chain dead-ends at an unexplained requirement — the gap an assessor asks about first. Needs are the legitimate roots, so they are exempt by type rather than by convention.";
        attribute predicateExpression = "downstream(derivesFrom)->isEmpty() or upstream(derivesFrom)->notEmpty() or conformsTo(MemoNeed)";
        constraint { true }
    }

    // ─── Causes ─────────────────────────────────────────────────────────
    //
    // Causes' ends are untyped because its CauseKind spans parts and items
    // (memo_fmea.sysml). These carry what the types cannot.

    constraint def CausesCauseKindRule :> MemoConsistencyRule {
        @MemoIdentity { :>> providedId = "CR-ONT-082"; }
        attribute tailoring = RuleTailoringKind::invariant;
        attribute domain = RuleDomainKind::modelling;
        attribute obligation = RuleObligationKind::recommended;
        attribute appliesTo = "Model";
        attribute severity = RuleSeverityKind::error;
        attribute rationaleText = "A cause is a risk-chain element (a failure mode, failure cause, hazard cause or fault-tree event) or a part that originates one (a component, a use error). A requirement or a behaviour causes nothing.";
        attribute predicateExpression = "sourcesOf(causes)->forAll(conformsTo(RiskItem) or conformsTo(MemoPart))";
        constraint { true }
    }
    constraint def CausesEffectKindRule :> MemoConsistencyRule {
        @MemoIdentity { :>> providedId = "CR-ONT-083"; }
        attribute tailoring = RuleTailoringKind::invariant;
        attribute domain = RuleDomainKind::modelling;
        attribute obligation = RuleObligationKind::recommended;
        attribute appliesTo = "Model";
        attribute severity = RuleSeverityKind::error;
        attribute rationaleText = "An effect is a link in a risk chain, or the fault-tree event a component originates. Not a component, not a requirement.";
        attribute predicateExpression = "targetsOf(causes)->forAll(conformsTo(RiskItem) or conformsTo(FaultTreeNode))";
        constraint { true }
    }

    // ─── Views and viewpoints ───────────────────────────────────────────

    // ISO 42010 conformance is many-to-many, but never empty: `MemoView.viewpointDefinition` is `[1..*]`. A view
    // that traces to a viewpoint is filed under it in Architect; one that traces to none has nowhere to be found.
    constraint def ViewTracesToViewpointRule :> MemoConsistencyRule {
        @MemoIdentity { :>> providedId = "CR-ONT-092"; }
        attribute tailoring = RuleTailoringKind::invariant;
        attribute domain = RuleDomainKind::modelling;
        attribute obligation = RuleObligationKind::recommended;
        attribute appliesTo = "MemoView";
        attribute severity = RuleSeverityKind::error;
        attribute rationaleText = "Every view traces to at least one viewpoint (ISO/IEC/IEEE 42010): the viewpoint says what the view is for and who reads it. A view with none cannot be filed under a viewpoint, so Architect lists it as uncategorised.";
        attribute predicateExpression = "attributes.viewpointDefinition != ''";
        constraint { true }

    }

    // ─── Operational levels (see the header) ─────────────────────────────

    constraint def UseCaseSubjectIsAtALevelRule :> MemoConsistencyRule {
        @MemoIdentity { :>> providedId = "CR-ONT-093"; }
        attribute tailoring = RuleTailoringKind::methodology;
        attribute domain = RuleDomainKind::modelling;
        attribute obligation = RuleObligationKind::recommended;
        attribute appliesTo = "UseCase";
        attribute severity = RuleSeverityKind::error;
        attribute rationaleText = "A use case is declared at a level, and its subject agrees: a clinical use case has an operational entity (the care team, the setting) as its subject, a system use case a system or a system of systems. A use case of neither type does not say whether it may name a product or carry a number, and a subject of the other level makes the declared type false.";
        attribute predicateExpression = "(conformsTo(ClinicalUseCase) and downstream(hasSubject)->forAll(conformsTo(OperationalEntity))) or (conformsTo(SystemUseCase) and downstream(hasSubject)->forAll(conformsTo(System) or conformsTo(SystemOfSystems)))";
        constraint { true }
    }
    constraint def LevelOneStepCarriesNoNumberRule :> MemoConsistencyRule {
        @MemoIdentity { :>> providedId = "CR-ONT-094"; }
        attribute tailoring = RuleTailoringKind::invariant;
        attribute domain = RuleDomainKind::modelling;
        attribute obligation = RuleObligationKind::recommended;
        attribute appliesTo = "OperativeAction";
        attribute severity = RuleSeverityKind::error;
        attribute rationaleText = "A step of a level-1 workflow is the shared baseline of every variant and carries no planned number: a gastric pouch takes a different time and succeeds at a different rate on each platform, so a number on the step would belong to no variant. Time and success are set on the level-2 activity that refines it.";
        attribute predicateExpression = "(attributes.expectedDuration == '' and attributes.plannedSuccessProbability == '') or not((upstream(composes)->exists(conformsTo(ClinicalWorkflow)) or upstream(performs)->exists(upstream(composes)->exists(conformsTo(ClinicalWorkflow))) or upstream(composes)->exists(upstream(performs)->exists(upstream(composes)->exists(conformsTo(ClinicalWorkflow))))))";
        constraint { true }
    }
    constraint def RealizerOfLevelOneStepIsLevelTwoRule :> MemoConsistencyRule {
        @MemoIdentity { :>> providedId = "CR-ONT-095"; }
        attribute tailoring = RuleTailoringKind::methodology;
        attribute domain = RuleDomainKind::modelling;
        attribute obligation = RuleObligationKind::recommended;
        attribute appliesTo = "OperativeAction";
        attribute severity = RuleSeverityKind::error;
        attribute rationaleText = "Whatever refines a level-1 step is itself at level 2: a level-1 step refined by another level-1 step, or by an activity of no workflow at all, skips the level that names the variant.";
        attribute predicateExpression = "not(downstream(realizes)->exists((upstream(composes)->exists(conformsTo(ClinicalWorkflow)) or upstream(performs)->exists(upstream(composes)->exists(conformsTo(ClinicalWorkflow))) or upstream(composes)->exists(upstream(performs)->exists(upstream(composes)->exists(conformsTo(ClinicalWorkflow))))))) or (upstream(composes)->exists(conformsTo(SystemWorkflow)) or upstream(performs)->exists(upstream(composes)->exists(conformsTo(SystemWorkflow))) or upstream(composes)->exists(upstream(performs)->exists(upstream(composes)->exists(conformsTo(SystemWorkflow)))))";
        constraint { true }
    }
    constraint def InternalSystemActivityPerformsAFunctionRule :> MemoConsistencyRule {
        @MemoIdentity { :>> providedId = "CR-ONT-096"; }
        attribute tailoring = RuleTailoringKind::methodology;
        attribute domain = RuleDomainKind::modelling;
        attribute obligation = RuleObligationKind::recommended;
        attribute appliesTo = "OperativeAction";
        attribute severity = RuleSeverityKind::warning;
        attribute rationaleText = "An activity that a system built by this organisation performs reaches level 3 by performing the system function that carries it out. An external system, a competitor's or a legacy platform, has no level 3 here and is not asked.";
        attribute predicateExpression = "not(upstream(performs)->exists((conformsTo(System) or conformsTo(SystemOfSystems)) and attributes.origin != 'SystemOriginKind::external')) or downstream(performs)->exists(conformsTo(SystemFunction))";
        constraint { true }
    }
    constraint def FunctionIsNotPerformedFromLevelOneRule :> MemoConsistencyRule {
        @MemoIdentity { :>> providedId = "CR-ONT-097"; }
        attribute tailoring = RuleTailoringKind::methodology;
        attribute domain = RuleDomainKind::modelling;
        attribute obligation = RuleObligationKind::recommended;
        attribute appliesTo = "SystemFunction";
        attribute severity = RuleSeverityKind::error;
        attribute rationaleText = "A system function is performed from a level-2 activity or from a step of a functional flow, never from a level-1 step: level 1 names no product, and a function is what a product does.";
        attribute predicateExpression = "upstream(performs)->forAll(not(conformsTo(OperativeAction) and (upstream(composes)->exists(conformsTo(ClinicalWorkflow)) or upstream(performs)->exists(upstream(composes)->exists(conformsTo(ClinicalWorkflow))) or upstream(composes)->exists(upstream(performs)->exists(upstream(composes)->exists(conformsTo(ClinicalWorkflow)))))))";
        constraint { true }
    }
    constraint def ProjectDeclaresOneCurrencyRule :> MemoConsistencyRule {
        @MemoIdentity { :>> providedId = "CR-ONT-098"; }
        attribute tailoring = RuleTailoringKind::invariant;
        attribute domain = RuleDomainKind::modelling;
        attribute obligation = RuleObligationKind::recommended;
        attribute appliesTo = "Model";
        attribute severity = RuleSeverityKind::error;
        attribute rationaleText = "A project states every amount in one currency, declared once as a currency unit. No conversion between currencies is modelled, so two currency units make every sum across them meaningless.";
        attribute predicateExpression = "allOfKind('CurrencyUnit')->size() <= 1";
        constraint { true }
    }
    constraint def LevelOneScenarioCarriesNoLikelihoodRule :> MemoConsistencyRule {
        @MemoIdentity { :>> providedId = "CR-ONT-099"; }
        attribute tailoring = RuleTailoringKind::invariant;
        attribute domain = RuleDomainKind::modelling;
        attribute obligation = RuleObligationKind::recommended;
        attribute appliesTo = "OperativeScenario";
        attribute severity = RuleSeverityKind::error;
        attribute rationaleText = "How likely a path is differs by platform (a robot and a laparoscopic tower do not convert to open at the same rate), so a scenario of a level-1 workflow carries no likelihood; it is set on the level-2 scenario of each variant.";
        attribute predicateExpression = "attributes.likelihood == '' or not(upstream(composes)->exists(conformsTo(ClinicalWorkflow)))";
        constraint { true }
    }
    constraint def LevelOneWorkflowCarriesNoCostRule :> MemoConsistencyRule {
        @MemoIdentity { :>> providedId = "CR-ONT-100"; }
        attribute tailoring = RuleTailoringKind::invariant;
        attribute domain = RuleDomainKind::modelling;
        attribute obligation = RuleObligationKind::recommended;
        attribute appliesTo = "OperationalWorkflow";
        attribute severity = RuleSeverityKind::error;
        attribute rationaleText = "What a procedure costs apart from its activities (set-up, capital per case) depends on the platform, so a level-1 workflow carries no per-procedure cost; it is set on the workflow of each level-2 variant.";
        attribute predicateExpression = "attributes.perProcedureCost == '' or not(conformsTo(ClinicalWorkflow))";
        constraint { true }
    }
    constraint def TradeStudyVariantRefinesEveryStepRule :> MemoConsistencyRule {
        @MemoIdentity { :>> providedId = "CR-ONT-101"; }
        attribute tailoring = RuleTailoringKind::methodology;
        attribute domain = RuleDomainKind::modelling;
        attribute obligation = RuleObligationKind::recommended;
        attribute appliesTo = "OperationalWorkflow";
        attribute severity = RuleSeverityKind::error;
        attribute rationaleText = "Every alternative of a trade study refines every level-1 step that any alternative of it refines, whether its activities are nested in its scenarios or performed by them. An alternative with a step missing reads as zero time and zero cost for it, so the study would prefer it for doing less.";
        attribute predicateExpression = "not(upstream(hasSubject)->exists(attributes.usageType == 'TradeStudy')) or upstream(hasSubject)->select(attributes.usageType == 'TradeStudy')->forAll(downstream(hasSubject)->forAll(downstream(composes)->forAll(downstream(realizes)->forAll(upstream(realizes)->exists(upstream(composes)->exists(id == subject.id) or upstream(performs)->exists(upstream(composes)->exists(id == subject.id))))) and downstream(composes)->forAll(downstream(performs)->forAll(downstream(realizes)->forAll(upstream(realizes)->exists(upstream(composes)->exists(id == subject.id) or upstream(performs)->exists(upstream(composes)->exists(id == subject.id))))))))";
        constraint { true }
    }
    constraint def WorkflowOwnsNoStepsOutsideScenariosRule :> MemoConsistencyRule {
        @MemoIdentity { :>> providedId = "CR-ONT-102"; }
        attribute tailoring = RuleTailoringKind::methodology;
        attribute domain = RuleDomainKind::modelling;
        attribute obligation = RuleObligationKind::recommended;
        attribute appliesTo = "OperativeAction";
        attribute severity = RuleSeverityKind::error;
        attribute rationaleText = "A workflow is the analysis of a use case (its equipment, environment and needs); the steps that carry it out are the tasks of a use scenario (IEC 62366-1 5.4). A step owned by the workflow itself belongs to no scenario, so it has no pre- or post-condition and no path it is on.";
        attribute predicateExpression = "not(upstream(composes)->exists(conformsTo(OperationalWorkflow))) or upstream(composes)->exists(conformsTo(OperativeScenario))";
        constraint { true }
    }
    constraint def WorkflowRealizesUseCaseOfItsLevelRule :> MemoConsistencyRule {
        @MemoIdentity { :>> providedId = "CR-ONT-103"; }
        attribute tailoring = RuleTailoringKind::methodology;
        attribute domain = RuleDomainKind::modelling;
        attribute obligation = RuleObligationKind::recommended;
        attribute appliesTo = "OperationalWorkflow";
        attribute severity = RuleSeverityKind::error;
        attribute rationaleText = "A workflow is the analysis of a use case and is at its level: a clinical workflow realizes a clinical use case, a system workflow a system use case. A workflow of the wrong level would carry a number the use case it serves may not, or hide a product from the baseline every variant is compared against.";
        attribute predicateExpression = "(conformsTo(ClinicalWorkflow) and downstream(realizesUseCase)->forAll(conformsTo(ClinicalUseCase))) or (conformsTo(SystemWorkflow) and downstream(realizesUseCase)->forAll(conformsTo(SystemUseCase)))";
        constraint { true }
    }
    #EnforcesClause dependency from WorkflowOwnsNoStepsOutsideScenariosRule to iec62366_1::iec62366_1Clause5::iec62366_1Clause5_4;
}
