// Regulatory coverage is project-profile dependent and is calculated by the
// completeness and coverage reports. A universal per-element constraint would
// incorrectly require every project to implement every standard pack, so this
// package declares no consistency constraints.
package memo_rules_coverage {
}
