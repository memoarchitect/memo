package connected_device_assurance {
    private import memo::*;

    requirement connectivityRequirement : Requirement {
        attribute redefines statement = "Define connectivity and cybersecurity boundaries";
    }
}
