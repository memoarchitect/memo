package infusion_pump_assurance {
    private import memo::*;

    requirement deliveryRequirement : Requirement {
        attribute redefines statement = "Define safe therapy delivery behavior";
    }
}
