// ROS 2 (Robot Operating System 2).
//
// The acceptance test for MEMO's extension point: a whole technology stack —
// nodes, messages, topics, quality of service, services, actions, and
// containerized deployment — landing without a single change to a base
// relation. `BuildsInto`, `DeploysTo`, and `ProvidesEnvironment` are reused
// exactly as the base declares them.
//
// Composition is by import. ROS builds on the messaging and container
// extensions and imports them PUBLICLY, so a project that imports
// `memo_extension_ros` has all three: their definitions are visible and their
// packages are selected. The dependency is stated once, here, and the KPAR
// build reads the same lines to record it. ROS communication specializes
// native MEMO item, port, and interface families; it does not invent
// publish/subscribe relations.
package memo_extension_ros {
    private import memo_core_stdlib_quantities::*;
    private import ScalarValues::*;

    private import memo_core_common::*;
    private import memo_core_enumerations::*;
    private import memo_architecture_functional_behavior::*;
    private import memo_architecture_logical_interfaces::*;
    private import memo_architecture_implementation_software_structure::*;
    private import memo_architecture_implementation_software_runtime::*;
    public import memo_extension_messaging::*;
    public import memo_extension_container::*;

    // ── Quality of service ──────────────────────────────────────────────
    //
    // Per-technology properties live in a typed `attribute def` on the
    // extension's own types. A typed profile can be validated, compared between
    // a publisher and a subscriber, and read by a tool; a property bag cannot.

    // TRANSIENT_LOCAL replays the last samples to a late-joining subscriber;
    // VOLATILE does not. The difference decides whether a node that restarts
    // sees the current state or waits for the next publication — which is a
    // safety-relevant fact when the topic carries a latched mode or setpoint.
    enum def RosDurabilityKind {
        enum volatile;
        enum transientLocal;
    }

    // RELIABILITY is not in the profile. ROS 2 RELIABLE resends until delivery
    // and BEST_EFFORT does not, which is the delivery guarantee the port
    // already states as `deliverySemantics`: bestEffort is atMostOnce and
    // reliable is atLeastOnce. Stating it a second time here let one port
    // say both and disagree.
    attribute def RosQosProfile {
        attribute durability : RosDurabilityKind;
        // The QoS contract: a sample is expected at least this often.
        attribute deadlineMs : DurationValue;
        // How long a publisher may be silent before subscribers treat it as
        // lost — ROS 2 liveliness lease duration.
        attribute livelinessLeaseMs : DurationValue;
        // Depth of the history buffer, KEEP_LAST(n) / KEEP_ALL.
        attribute historyDepth : Integer;
    }

    // ── Nodes, messages, topics, and endpoint roles ────────────────────

    // A ROS node. `runtimeKind` is deliberately NOT bound: a node may run as
    // its own process or be composed with others into a single container
    // process, and which one it is is a design decision the model should
    // record rather than a fact the type can assert.
    part def RosNode specializes SoftwareComponent {
        @MemoIdentity { :>> label = "ROS node"; }
        attribute nodeNamespace : String;
        // Whether the node implements the managed-node lifecycle
        // (unconfigured / inactive / active / finalized). A lifecycle-managed
        // node can be brought up in a defined order and held inactive until
        // its preconditions hold, which is how a robot reaches a safe state.
        attribute lifecycleManaged : Boolean;
        attribute executorModel : String;
    }

    // A definition is the ROS message contract (`LaserScan`, `Twist`, ...).
    // A named item usage of that definition is a deployed topic (`/scan`).
    // Individual deliveries are native flows/messages between ports that
    // reference the same topic usage.
    abstract item def RosMessage specializes MessagingMessage {
        @MemoIdentity { :>> label = "ROS message"; }
        attribute rosTypeName : String;
    }

    port def RosPublisher specializes MessagingPublisher {
        @MemoIdentity { :>> label = "ROS publisher"; }
        attribute offeredQos : RosQosProfile;
    }

    port def RosSubscriber specializes MessagingSubscriber {
        @MemoIdentity { :>> label = "ROS subscriber"; }
        attribute requestedQos : RosQosProfile;
    }

    interface def RosTopicInterface specializes MessagingTopicInterface {
        @MemoIdentity { :>> label = "ROS topic interface"; }
        end rosPublisher : RosPublisher :>> publisher;
        end rosSubscriber : RosSubscriber :>> subscriber;
        // A topic goes publisher to subscriber, always.
        attribute :>> direction default DirectionKind::output;
    }

    // ── Services: one correlated request/reply contract ────────────────
    abstract item def RosServiceRequest specializes RosMessage {
        @MemoIdentity { :>> label = "ROS service request"; }
    }
    abstract item def RosServiceResponse specializes RosMessage {
        @MemoIdentity { :>> label = "ROS service response"; }
    }

    port def RosServiceClient specializes SoftwarePort {
        @MemoIdentity { :>> label = "ROS service client"; }
        out item request : RosServiceRequest;
        in item response : RosServiceResponse;
        attribute serviceName : String;
    }

    port def RosServiceServer specializes SoftwarePort {
        @MemoIdentity { :>> label = "ROS service server"; }
        in item request : RosServiceRequest;
        out item response : RosServiceResponse;
        attribute serviceName : String;
    }

    interface def RosServiceInterface specializes SoftwareInterface {
        @MemoIdentity { :>> label = "ROS service interface"; }
        end client : RosServiceClient :>> source;
        end server : RosServiceServer :>> target;
        flow rosServiceRequestFlow of RosServiceRequest from client.request to server.request;
        flow rosServiceResponseFlow of RosServiceResponse from server.response to client.response;
    }

    // ── Actions: long-running goal protocol ─────────────────────────────
    // ROS 2 realizes an action through goal/result/cancel services plus
    // feedback/status topics. The port exposes those distinct native message
    // features, so an action cannot be mistaken for a two-message service.
    abstract item def RosActionGoal specializes RosMessage {
        @MemoIdentity { :>> label = "ROS action goal"; }
    }
    abstract item def RosActionAcceptance specializes RosMessage {
        @MemoIdentity { :>> label = "ROS action acceptance"; }
    }
    abstract item def RosActionFeedback specializes RosMessage {
        @MemoIdentity { :>> label = "ROS action feedback"; }
    }
    abstract item def RosActionResult specializes RosMessage {
        @MemoIdentity { :>> label = "ROS action result"; }
    }
    abstract item def RosActionCancel specializes RosMessage {
        @MemoIdentity { :>> label = "ROS action cancel"; }
    }
    abstract item def RosActionStatus specializes RosMessage {
        @MemoIdentity { :>> label = "ROS action status"; }
    }

    port def RosActionClient specializes SoftwarePort {
        @MemoIdentity { :>> label = "ROS action client"; }
        out item goal : RosActionGoal;
        in item acceptance : RosActionAcceptance;
        in item feedback : RosActionFeedback;
        in item result : RosActionResult;
        out item cancel : RosActionCancel;
        in item actionStatus : RosActionStatus;
        attribute actionName : String;
    }

    port def RosActionServer specializes SoftwarePort {
        @MemoIdentity { :>> label = "ROS action server"; }
        in item goal : RosActionGoal;
        out item acceptance : RosActionAcceptance;
        out item feedback : RosActionFeedback;
        out item result : RosActionResult;
        in item cancel : RosActionCancel;
        out item actionStatus : RosActionStatus;
        attribute actionName : String;
    }

    interface def RosActionInterface specializes SoftwareInterface {
        @MemoIdentity { :>> label = "ROS action interface"; }
        end client : RosActionClient :>> source;
        end server : RosActionServer :>> target;
        flow rosActionGoalFlow of RosActionGoal from client.goal to server.goal;
        flow rosActionAcceptanceFlow of RosActionAcceptance from server.acceptance to client.acceptance;
        flow rosActionFeedbackFlow of RosActionFeedback from server.feedback to client.feedback;
        flow rosActionCancelFlow of RosActionCancel from client.cancel to server.cancel;
        flow rosActionResultFlow of RosActionResult from server.result to client.result;
        flow rosActionStatusFlow of RosActionStatus from server.actionStatus to client.actionStatus;
    }

    abstract state def RosActionExecution specializes MemoState {
        @MemoIdentity { :>> label = "ROS action execution"; }
    }
    state def RosActionAccepted specializes RosActionExecution {
        @MemoIdentity { :>> label = "ROS action accepted"; }
    }
    state def RosActionExecuting specializes RosActionExecution {
        @MemoIdentity { :>> label = "ROS action executing"; }
    }
    state def RosActionCanceling specializes RosActionExecution {
        @MemoIdentity { :>> label = "ROS action canceling"; }
    }
    state def RosActionSucceeded specializes RosActionExecution {
        @MemoIdentity { :>> label = "ROS action succeeded"; }
    }
    state def RosActionCanceled specializes RosActionExecution {
        @MemoIdentity { :>> label = "ROS action canceled"; }
    }
    state def RosActionAborted specializes RosActionExecution {
        @MemoIdentity { :>> label = "ROS action aborted"; }
    }

    // ── Deployment ──────────────────────────────────────────────────────
    //
    // Nothing below declares a relation. The base's three deployment
    // relations already say everything a ROS deployment needs:
    //   BuildsInto          SoftwareModule -> RosContainerImage
    //   DeploysTo           RosContainerImage -> ProcessingNode
    //   ProvidesEnvironment ProcessingNode -> RosContainerRuntime
    // That is the proof the base is factored correctly.
    part def RosContainerImage specializes ContainerImage {
        @MemoIdentity { :>> label = "ROS container image"; }
        // humble, iron, jazzy, rolling.
        attribute rosDistribution : String;
        // The workspace overlay the image was built from.
        attribute workspaceOverlay : String;
    }

    part def RosContainerRuntime specializes ContainerRuntime {
        @MemoIdentity { :>> label = "ROS container runtime"; }
        attribute rosDistribution : String;
        // The RMW implementation below ROS 2 — rmw_fastrtps_cpp,
        // rmw_cyclonedds_cpp. QoS is enforced here, so it is part of any
        // argument that a QoS profile is actually honoured.
        attribute rmwImplementation : String;
        // ROS_DOMAIN_ID. Two robots sharing a domain see each other's topics,
        // which is a hazard on a shared network and not visible in any node.
        attribute rosDomainId : Integer;
    }
}
