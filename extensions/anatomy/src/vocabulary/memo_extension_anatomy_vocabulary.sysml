// GENERATED by scripts/build_fma_index.py from the Foundational Model of Anatomy (FMA) 5.1.0,
// University of Washington Structural Informatics Group, http://purl.org/sig/ont/fma.owl,
// CC BY 4.0 (https://creativecommons.org/licenses/by/4.0/). Modified: converted from OWL to
// SysML v2. Do not edit; regenerate.
//
// The root every generated FMA class specializes, with one abstract feature per FMA
// relation. A relation that is a kind of `part` is composition; any other is a reference.
// The features subset each other as FMA's relations do (`regional_part` is a `part`), so a
// query over `partFeatures` reaches every kind of part.
package memo_extension_anatomy_vocabulary {
    private import memo_core_common::*;

    abstract part def AnatomyEntity specializes MemoPart {
        @MemoIdentity { :>> label = "Anatomy entity"; }
        abstract ref part adheresToFeatures : AnatomyEntity[0..*] :> connectedToFeatures;
        abstract ref part adjacentToFeatures : AnatomyEntity[0..*];
        abstract ref part afferentToFeatures : AnatomyEntity[0..*] :> connectedToFeatures;
        abstract ref part anatomicalEntityObservedFeatures : AnatomyEntity[0..*];
        abstract ref part anatomicalLandmarkForFeatures : AnatomyEntity[0..*];
        abstract ref part anatomicalPlaneFeatures : AnatomyEntity[0..*];
        abstract ref part anteriorToFeatures : AnatomyEntity[0..*] :> hasLocationFeatures;
        abstract ref part anteroinferiorToFeatures : AnatomyEntity[0..*] :> hasLocationFeatures;
        abstract ref part anterolateralToFeatures : AnatomyEntity[0..*] :> hasLocationFeatures;
        abstract ref part anteromedialToFeatures : AnatomyEntity[0..*] :> hasLocationFeatures;
        abstract ref part anterosuperiorToFeatures : AnatomyEntity[0..*] :> hasLocationFeatures;
        abstract ref part arterialSupplyFeatures : AnatomyEntity[0..*] :> connectedToFeatures;
        abstract ref part articulatesWithFeatures : AnatomyEntity[0..*] :> connectedToFeatures;
        abstract ref part attachesToFeatures : AnatomyEntity[0..*] :> connectedToFeatures;
        abstract ref part boundedByFeatures : AnatomyEntity[0..*];
        abstract part branchFeatures : AnatomyEntity[0..*] :> regionalPartFeatures;
        abstract ref part branchContinuityFeatures : AnatomyEntity[0..*];
        abstract ref part connectedToFeatures : AnatomyEntity[0..*];
        abstract ref part connectingPartFeatures : AnatomyEntity[0..*];
        abstract ref part connectionTypeFeatures : AnatomyEntity[0..*];
        abstract part constitutionalPartFeatures : AnatomyEntity[0..*] :> part_Features;
        abstract ref part containedInFeatures : AnatomyEntity[0..*];
        abstract ref part continuousDistallyWithFeatures : AnatomyEntity[0..*] :> continuousWithFeatures;
        abstract ref part continuousWithFeatures : AnatomyEntity[0..*] :> connectedToFeatures;
        abstract ref part correspondsToFeatures : AnatomyEntity[0..*];
        abstract ref part derivesFeatures : AnatomyEntity[0..*];
        abstract ref part developmentTypeFeatures : AnatomyEntity[0..*];
        abstract ref part developmentalFusionFeatures : AnatomyEntity[0..*];
        abstract ref part developmentalStageOfFeatures : AnatomyEntity[0..*];
        abstract ref part developsFromFeatures : AnatomyEntity[0..*];
        abstract ref part directLeftOfFeatures : AnatomyEntity[0..*] :> hasLocationFeatures;
        abstract ref part directRightOfFeatures : AnatomyEntity[0..*] :> hasLocationFeatures;
        abstract ref part distalToFeatures : AnatomyEntity[0..*] :> hasLocationFeatures;
        abstract ref part drainsIntoFeatures : AnatomyEntity[0..*];
        abstract ref part externalToFeatures : AnatomyEntity[0..*];
        abstract ref part continuousSuperiorlyWithFeatures : AnatomyEntity[0..*] :> continuousWithFeatures;
        abstract ref part formsFeatures : AnatomyEntity[0..*];
        abstract ref part fullGrownPhenotypeFeatures : AnatomyEntity[0..*];
        abstract ref part fusesWithFeatures : AnatomyEntity[0..*];
        abstract ref part fusionOfFeatures : AnatomyEntity[0..*];
        abstract ref part germOriginFeatures : AnatomyEntity[0..*];
        abstract ref part hasDirectCellShapeFeatures : AnatomyEntity[0..*];
        abstract ref part hasInsertionFeatures : AnatomyEntity[0..*] :> connectedToFeatures;
        abstract ref part hasLocationFeatures : AnatomyEntity[0..*];
        abstract ref part hasOriginFeatures : AnatomyEntity[0..*] :> connectedToFeatures;
        abstract ref part hasProjectionFeatures : AnatomyEntity[0..*];
        abstract ref part inferiorToFeatures : AnatomyEntity[0..*] :> hasLocationFeatures;
        abstract ref part inferolateralToFeatures : AnatomyEntity[0..*] :> hasLocationFeatures;
        abstract ref part inferomedialToFeatures : AnatomyEntity[0..*] :> hasLocationFeatures;
        abstract ref part inherent3DShapeFeatures : AnatomyEntity[0..*];
        abstract ref part inputFromFeatures : AnatomyEntity[0..*];
        abstract ref part isBoundaryOfFeatures : AnatomyEntity[0..*];
        abstract ref part lateralToFeatures : AnatomyEntity[0..*] :> hasLocationFeatures;
        abstract ref part leftLateralToFeatures : AnatomyEntity[0..*] :> lateralToFeatures;
        abstract ref part leftMedialToFeatures : AnatomyEntity[0..*] :> medialToFeatures;
        abstract ref part locatedInFeatures : AnatomyEntity[0..*];
        abstract ref part lymphaticDrainageFeatures : AnatomyEntity[0..*] :> connectedToFeatures;
        abstract ref part maturesFromFeatures : AnatomyEntity[0..*] :> developsFromFeatures;
        abstract ref part medialToFeatures : AnatomyEntity[0..*] :> hasLocationFeatures;
        abstract part memberFeatures : AnatomyEntity[0..*] :> part_Features;
        abstract ref part mergesWithFeatures : AnatomyEntity[0..*];
        abstract ref part mergingOfFeatures : AnatomyEntity[0..*];
        abstract ref part muscleAttachmentFeatures : AnatomyEntity[0..*] :> connectedToFeatures;
        abstract ref part nerveSupplyFeatures : AnatomyEntity[0..*] :> connectedToFeatures;
        abstract ref part nucleusOfOriginOfFeatures : AnatomyEntity[0..*];
        abstract ref part nucleusOfTerminationOfFeatures : AnatomyEntity[0..*];
        abstract ref part orientationFeatures : AnatomyEntity[0..*];
        abstract ref part outputToFeatures : AnatomyEntity[0..*];
        abstract part part_Features : AnatomyEntity[0..*];
        abstract ref part posteriorToFeatures : AnatomyEntity[0..*] :> hasLocationFeatures;
        abstract ref part posteroinferiorToFeatures : AnatomyEntity[0..*] :> hasLocationFeatures;
        abstract ref part posterolateralToFeatures : AnatomyEntity[0..*] :> hasLocationFeatures;
        abstract ref part posteromedialToFeatures : AnatomyEntity[0..*] :> hasLocationFeatures;
        abstract ref part posterosuperiorToFeatures : AnatomyEntity[0..*] :> hasLocationFeatures;
        abstract ref part primarySegmentalSupplyFeatures : AnatomyEntity[0..*];
        abstract ref part projectsToFeatures : AnatomyEntity[0..*];
        abstract ref part proximalToFeatures : AnatomyEntity[0..*] :> hasLocationFeatures;
        abstract ref part receivesInputFromFeatures : AnatomyEntity[0..*];
        abstract part regionalPartFeatures : AnatomyEntity[0..*] :> part_Features;
        abstract ref part relatedDevelopmentalEntityFeatures : AnatomyEntity[0..*];
        abstract ref part relatedObjectFeatures : AnatomyEntity[0..*];
        abstract ref part relatedPartFeatures : AnatomyEntity[0..*];
        abstract ref part rightLateralToFeatures : AnatomyEntity[0..*] :> lateralToFeatures;
        abstract ref part rightMedialToFeatures : AnatomyEntity[0..*] :> medialToFeatures;
        abstract ref part secondarySegmentalSupplyFeatures : AnatomyEntity[0..*];
        abstract ref part segmentalCompositionFeatures : AnatomyEntity[0..*];
        abstract ref part segmentalContributionFromFeatures : AnatomyEntity[0..*];
        abstract ref part segmentalInnervationFeatures : AnatomyEntity[0..*];
        abstract ref part segmentalSupplyFeatures : AnatomyEntity[0..*];
        abstract ref part sensoryNerveSupplyFeatures : AnatomyEntity[0..*];
        abstract ref part superiorToFeatures : AnatomyEntity[0..*] :> hasLocationFeatures;
        abstract ref part superolateralToFeatures : AnatomyEntity[0..*] :> hasLocationFeatures;
        abstract ref part superomedialToFeatures : AnatomyEntity[0..*] :> hasLocationFeatures;
        abstract ref part surroundedByFeatures : AnatomyEntity[0..*];
        abstract ref part transformsFromFeatures : AnatomyEntity[0..*] :> developsFromFeatures;
        abstract part tributaryFeatures : AnatomyEntity[0..*] :> regionalPartFeatures;
        abstract ref part tributaryContinuityFeatures : AnatomyEntity[0..*];
        abstract ref part unionFeatures : AnatomyEntity[0..*];
        abstract ref part unitesWithFeatures : AnatomyEntity[0..*];
        abstract ref part venousDrainageFeatures : AnatomyEntity[0..*] :> connectedToFeatures;
    }
}
