// Messaging vocabulary, technology-neutral across DDS, MQTT, AMQP and Kafka.
// It specializes native item, port, and interface families; publication and
// subscription are expressed by port direction plus native flows/messages.
//
// `deliverySemantics` and `topicStructure` are here because neither is a
// property of a component: a component does not have a topic, a publication
// does; a component does not have delivery semantics, the channel it publishes
// over does.
package memo_extension_messaging {
    private import memo_core_stdlib_quantities::*;
    private import ScalarValues::*;

    private import memo_core_common::*;
    private import memo_core_enumerations::*;
    private import memo_architecture_logical_interfaces::*;
    private import memo_architecture_implementation_software_structure::*;
    private import memo_architecture_implementation_software_runtime::*;

    // What a broker guarantees about each message. Safety-relevant: an alarm
    // published at-most-once can be silently dropped, and an at-least-once
    // command can be applied twice.
    enum def MessagingDeliveryKind {
        enum atMostOnce;
        enum atLeastOnce;
        enum exactlyOnce;
    }

    // Message/payload definition. A named topic is an item usage of a concrete
    // message definition; the definition states the schema, while the usage
    // supplies the deployed topic identity.
    item def MessagingMessage specializes DataItem {
        @MemoIdentity { :>> label = "Messaging message"; }
        attribute messageSchema : String;
    }

    // Endpoint roles. Direction is native on both the port's payload feature
    // and the port usage placed on a component. The shared `topic` reference
    // points every endpoint at the same named item usage.
    port def MessagingPublisher specializes SoftwarePort {
        @MemoIdentity { :>> label = "Messaging publisher"; }
        out item payload : MessagingMessage;
        ref item topic : MessagingMessage;
        attribute deliverySemantics : MessagingDeliveryKind;
        attribute publishRateHz : FrequencyValue;
    }

    port def MessagingSubscriber specializes SoftwarePort {
        @MemoIdentity { :>> label = "Messaging subscriber"; }
        in item payload : MessagingMessage;
        ref item topic : MessagingMessage;
        attribute deliverySemantics : MessagingDeliveryKind;
        attribute lossBehaviour : String;
    }

    interface def MessagingTopicInterface specializes SoftwareInterface {
        @MemoIdentity { :>> label = "Messaging topic interface"; }
        end publisher : MessagingPublisher :>> source;
        end subscriber : MessagingSubscriber :>> target;
        flow messagingMessageFlow of MessagingMessage from publisher.payload to subscriber.payload;
    }

    part def MessagingBroker specializes SoftwareComponent {
        @MemoIdentity { :>> label = "Messaging broker"; }
        attribute :>> runtimeKind = RuntimeKind::messageBroker;
        attribute brokerProduct : String;
        attribute persistenceEnabled : Boolean;
    }

}
