package memo_extension_messaging_methodology {
    private import ScalarValues::*;
    private import memo_methodology_core::*;
    private import memo_methodology_profiles::*;
    private import memo_core_enumerations::*;

    private import memo_core_common::*;
    private import memo_core_common::MemoIdentity;
    part messagingExtensionMethod : MethodologyDefinition {
        @MemoIdentity { :>> providedId = "EXT-MESSAGING-001"; :>> label = "MessagingExtension"; }
        attribute :>> version = "0.13.2";
        attribute :>> domain = "publish/subscribe messaging";
        doc /* Adds message items, publisher/subscriber ports, topic interfaces, brokers, and delivery semantics. */
        ref :>> baseMethodology = mdDefaultDefinition;
        attribute :>> scopeMode = ScopeModeKind::explicit;
        attribute :>> includedModule = "memo_extension_messaging";
    }
}
