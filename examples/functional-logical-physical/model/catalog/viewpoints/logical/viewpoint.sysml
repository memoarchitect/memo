// logical viewpoint.
//
// This project does not define its own viewpoint here; it binds the reusable
// MEMO viewpoint that frames these concerns. The views it governs sit beneath
// `views/`.
package memo_examples_functional_logical_physical_viewpoints_logical {
    public import memo_viewpoints_logical_logical_viewpoint::*;
}
