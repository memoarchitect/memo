// Software Only Medical Device — model identity and method binding.
//
// The native entrypoint. The imports name what this project contains and the
// binding names the methodology it is governed by. No YAML file participates.
package memo_examples_software_only_medical_device_project {
    private import memo::*;
    private import ScalarValues::*;


    // The project's own content, imported so the catalog is one reachable
    // closure from a single entrypoint.
    private import memo_examples_software_only_medical_device_viewpoints_logical_views_software_only_medical_device_overview::*;

    // The cloud extension supplies CloudService, which is what the grading
    // service is. Importing it publicly here is what brings it into the
    // project, its definitions and its selection alike.
    public import memo_extension_cloud::*;
    part projectBinding : ModelMethodBinding {
        @MemoIdentity { :>> providedId = "PMB-MEDICAL-DEVICE-001"; :>> label = "Software only medical device model method binding"; }
        attribute :>> modelName = "Software Only Medical Device";
        ref :>> selectedMethodology = mdDefaultDefinition;
        attribute :>> scopeMode = ScopeModeKind::explicit;
    }
}
