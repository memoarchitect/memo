// Public entry point for this example. Keep model content in catalog/ and views in viewpoints/.
package memo_examples_software_only_medical_device_parent {
    public import memo_examples_software_only_medical_device::*;
}
