// Verification and validation: cases and the evidence they produce.
package memo_examples_ui_screen_regions_assurance_verification_validation {
    private import memo::*;
    private import memo_examples_ui_screen_regions_assurance_safety_risk::*;
    private import memo_examples_ui_screen_regions_architecture_functional_functions::*;
    private import memo_examples_ui_screen_regions_assurance_requirements::*;
    private import ScalarValues::*;
    private import memo_core_dimensions::*;   // ElementStatusKind



    verification vcRateChange : VerificationCase {
        @MemoIdentity { :>> providedId = "UIR-VER-001"; :>> label = "Verify rate change confirmation"; }
        attribute :>> methodKind = MemoVerificationMethodKind::test;
        attribute :>> acceptanceCriteria = "A rate change cannot reach the controller until the displayed value is explicitly confirmed.";
        attribute :>> status = ElementStatusKind::approved;

        subject verified : Base::Anything[*] = (rcRateConfirm, fnManageInfusionDisplay.fnSetInfusionRate, fnManageInfusionDisplay);
    }

    part evRateChange : MemoEvidence {
        attribute :>> evidenceKind = EvidenceKind::evidence;
        @MemoIdentity { :>> providedId = "UIR-EV-001"; :>> label = "Rate change confirmation test record"; }
        attribute :>> version = "0.1.0";
        attribute :>> evidenceType = "test record";
        attribute :>> integrityStatus = "planned";
    }

    verification vcDrugLibrarySelection : VerificationCase {
        @MemoIdentity { :>> providedId = "VER-002"; :>> label = "Verify care area drug library selection"; }
        attribute :>> methodKind = MemoVerificationMethodKind::test;
        attribute :>> acceptanceCriteria = "Only enabled care-area drug and concentration records are selectable, and every selection supplies the matching dosing limits.";
        attribute :>> status = ElementStatusKind::approved;

        subject verified : Base::Anything[*] = (rcDrugLibraryGuard, fnManageInfusionDisplay.fnValidateDrugSelection);
    }

    part evDrugLibrarySelection : MemoEvidence {
        attribute :>> evidenceKind = EvidenceKind::evidence;
        @MemoIdentity { :>> providedId = "EVD-002"; :>> label = "Drug library selection test record"; }
        attribute :>> version = "0.1.0";
        attribute :>> evidenceType = "test record";
        attribute :>> integrityStatus = "planned";
    }

    verification vcInfusionStatusContent : VerificationCase {
        @MemoIdentity { :>> providedId = "VER-003"; :>> label = "Verify infusion status content and freshness"; }
        attribute :>> methodKind = MemoVerificationMethodKind::test;
        attribute :>> acceptanceCriteria = "Time, battery, active rate, drug identity, and total delivered volume satisfy their content, accuracy, and latency criteria under normal and threshold-transition conditions.";
        attribute :>> status = ElementStatusKind::approved;

        objective { verify reqActiveRateDisplay; verify reqDrugIdentityDisplay; verify reqVolumeDisplay; verify reqTimeDisplay; verify reqTimeAccuracy; verify reqBatteryStatusDisplay; verify reqBatteryWarningPerformance; }
        subject verified : Base::Anything[*] = (rcLowBatteryProminence, rcDisplayFreshnessMonitor, rcClockFreshnessCheck, fnManageInfusionDisplay.fnPresentDeliveryStatus, fnManageInfusionDisplay.fnPresentLocalTime, fnManageInfusionDisplay.fnPresentBatteryStatus);
    }

    part evInfusionStatusContent : MemoEvidence {
        attribute :>> evidenceKind = EvidenceKind::evidence;
        @MemoIdentity { :>> providedId = "EVD-003"; :>> label = "Infusion status display test record"; }
        attribute :>> version = "0.1.0";
        attribute :>> evidenceType = "test record";
        attribute :>> integrityStatus = "planned";
    }

}
