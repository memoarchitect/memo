// The requirements viewpoint frames stakeholder needs and their derivation, satisfaction, and verification.
//
// This project does not define its own viewpoint here; it binds the reusable
// MEMO viewpoint that already frames these concerns. The views this project
// governs with it sit beneath `views/`.
package memo_examples_ui_screen_regions_viewpoints_requirements {
    public import memo_viewpoints_requirements_requirements_viewpoint::*;
}
