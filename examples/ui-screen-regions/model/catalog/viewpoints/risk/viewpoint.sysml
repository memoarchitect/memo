// The risk viewpoint frames use errors, hazards, controls, and the evidence that they hold.
//
// This project does not define its own viewpoint here; it binds the reusable
// MEMO viewpoint that already frames these concerns. The views this project
// governs with it sit beneath `views/`.
package memo_examples_ui_screen_regions_viewpoints_risk {
    public import memo_viewpoints_risk_risk_viewpoint::*;
}
