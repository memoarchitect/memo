// The UI layout viewpoint frames how a captured screen is marked up: element geometry, disclosure, and the design record attached to each region.
//
// This project does not define its own viewpoint here; it binds the reusable
// MEMO viewpoint that already frames these concerns. The views this project
// governs with it sit beneath `views/`.
package memo_examples_ui_screen_regions_viewpoints_ui_layout {
    public import memo_viewpoints_ui_layout_ui_layout_viewpoint::*;
}
