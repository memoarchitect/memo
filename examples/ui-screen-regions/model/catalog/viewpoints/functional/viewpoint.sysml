// The functional viewpoint frames the system function tree and its allocation.
//
// This project does not define its own viewpoint here; it binds the reusable
// MEMO viewpoint that already frames these concerns. The views this project
// governs with it sit beneath `views/`.
package memo_examples_ui_screen_regions_viewpoints_functional {
    public import memo_viewpoints_functional_functional_viewpoint::*;
}
