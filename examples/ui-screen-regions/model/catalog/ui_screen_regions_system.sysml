package memo_examples_ui_screen_regions_ui_screen_regions_system {
    part def UiScreenRegionsSystem specializes memo_architecture_logical_structure::System {
        attribute :>> systemBoundaryDescription = "The infusion pump whose screens this example marks up.";
    }
}
