// Public entry point for this example. Keep model content in catalog/ and views in viewpoints/.
package memo_examples_ui_screen_regions_parent {
    public import memo_examples_ui_screen_regions::*;
}
