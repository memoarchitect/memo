// The manipulator: grasps a workpiece with its gripper and reports each grasp. It imports the family's shared package
// only.
package robot_cell_family_systems_manipulation_manipulation_system {
    private import memo::*;
    private import robot_cell_family_shared::*;

    part def ManipulatorSystem specializes System {
        @MemoIdentity { :>> providedId = "RCF-MAN-001"; :>> label = "Manipulator System"; }
        attribute :>> systemBoundaryDescription = "Arm controller, teach pendant and the gripper drive cable.";
        port pGraspEventOut : GraspEventPort;
        part motionController : LogicalComponent :> component {
            @MemoIdentity { :>> providedId = "RCF-MAN-LC-001"; :>> label = "Motion Controller"; }
            attribute :>> responsibility = "Regulate delivered power and duration, and report each delivery.";
        }
        allocate fnExecuteGrasp to motionController;
        part gripperDrive : LogicalComponent :> component {
            @MemoIdentity { :>> providedId = "RCF-MAN-LC-002"; :>> label = "Gripper Drive"; }
            attribute :>> responsibility = "Close and open the gripper on the controller's command.";
        }
        connection : LogicalConnector connect motionController to gripperDrive {
            attribute :>> contentKind = FlowContentKind::command;
            attribute :>> direction = DirectionKind::output;
        }
    }

    action fnExecuteGrasp : SystemFunction {
        @MemoIdentity { :>> providedId = "RCF-MAN-F-001"; :>> label = "Execute Grasp"; }
        out graspEventOut : GraspEvent;
        attribute :>> outputDescription = "Grasp made within the set force and time limits, and the event that records it";
    }

    use case ucExecuteGrasp : SystemUseCase {
        @MemoIdentity { :>> providedId = "RCF-MAN-UC-001"; :>> label = "Execute Grasp"; }
        attribute :>> useCaseKind = UseCaseKind::care;
        subject :>> supportingSystem : ManipulatorSystem;
        actor operator = cellOperator;
    }
}
