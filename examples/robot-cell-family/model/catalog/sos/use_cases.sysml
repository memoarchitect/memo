// Clinical use cases: their subject is the system of systems, and each
// includes the system use cases it is made of.
package robot_cell_family_sos_use_cases {
    private import memo::*;
    private import robot_cell_family_shared::*;
    private import robot_cell_family_sos::*;
    private import robot_cell_family_systems_navigation_navigation_system::*;
    private import robot_cell_family_systems_manipulation_manipulation_system::*;
    private import robot_cell_family_systems_perception_perception_system::*;

    use case ucPerformPickAndPlace : SystemUseCase {
        @MemoIdentity { :>> providedId = "RCF-UC-001"; :>> label = "Perform Pick And Place"; }
        attribute :>> useCaseKind = UseCaseKind::care;
        attribute :>> goalStatement = "Move a workpiece by mapping the cell and grasping it.";
        subject :>> supportingSystem = robotCell;
        actor operator = cellOperator;
        actor assistant = cellTechnician;
        include ucRecordRun { subject :>> supportingSystem = robotCell.perception; }
        include ucAcquireMap { subject :>> supportingSystem = robotCell.navigation; }
        include ucExecuteGrasp { subject :>> supportingSystem = robotCell.manipulation; }
    }
}
