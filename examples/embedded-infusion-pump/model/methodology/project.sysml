// Embedded Infusion Pump — model identity and method binding.
//
// The native entrypoint. The imports name what this project contains and the
// binding names the methodology it is governed by. No YAML file participates.
package memo_examples_embedded_infusion_pump_project {
    private import memo::*;
    private import ScalarValues::*;


    // The project's own content, imported so the catalog is one reachable
    // closure from a single entrypoint.
    private import memo_examples_embedded_infusion_pump_viewpoints_logical_views_embedded_infusion_pump_overview::*;

    part projectBinding : ModelMethodBinding {
        @MemoIdentity { :>> providedId = "PMB-INFUSION-PUMP-001"; :>> label = "Embedded infusion pump model method binding"; }
        attribute :>> modelName = "Embedded Infusion Pump";
        ref :>> selectedMethodology = mdDefaultDefinition;
        attribute :>> scopeMode = ScopeModeKind::explicit;
    }
}
