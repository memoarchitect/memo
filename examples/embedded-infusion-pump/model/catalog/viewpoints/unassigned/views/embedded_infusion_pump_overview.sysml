package memo_examples_embedded_infusion_pump_viewpoints_unassigned_views_embedded_infusion_pump_overview {
    private import memo_examples_embedded_infusion_pump::*;
    private import memo_viewpoints_definitions::*;
    private import memo_viewpoints_logical_logical_viewpoint::*;
    private import memo_core_enumerations::*;
    view embeddedInfusionPumpOverview : MemoDiagramView { expose memo_examples_embedded_infusion_pump::*; attribute depth = 2; attribute :>> viewKind = DiagramViewKind::general; attribute :>> diagramType = "bdd"; ref :>> viewpointDefinition = logicalArchitectureViewpoint; }
}
