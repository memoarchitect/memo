package memo_examples_nested_architecture_dsm_nested_architecture_dsm_system {
    part def NestedArchitectureDsmSystem specializes memo_architecture_logical_structure::System {
        attribute :>> systemBoundaryDescription = "The small infusion pump this example uses to exercise the two matrix views.";
    }
}
