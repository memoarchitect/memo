// shared viewpoint.
//
// This project does not define its own viewpoint here; it binds the reusable
// MEMO viewpoint that frames these concerns. The views it governs sit beneath
// `views/`.
package memo_examples_sysml_diagram_samples_viewpoints_shared {
    public import memo_viewpoints_functional_functional_viewpoint::*;
}
