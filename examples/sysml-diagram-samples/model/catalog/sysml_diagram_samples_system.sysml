package memo_examples_sysml_diagram_samples_sysml_diagram_samples_system {
    part def SysmlDiagramSamplesSystem specializes memo_architecture_logical_structure::System {
        attribute :>> systemBoundaryDescription = "The set of small systems this project draws to show each diagram type.";
    }
}
