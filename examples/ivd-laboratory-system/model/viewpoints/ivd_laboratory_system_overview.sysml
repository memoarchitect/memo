package memo_examples_ivd_laboratory_system_viewpoints {
    private import memo_examples_ivd_laboratory_system::*;
    private import memo_viewpoints_definitions::*;
    private import memo_core_enumerations::*;
    view ivdLaboratorySystemOverview : MemoDiagramView { expose memo_examples_ivd_laboratory_system::*; attribute depth = 2; attribute :>> title = "IVD Laboratory System Overview"; attribute :>> viewKind = DiagramViewKind::interconnection; attribute :>> diagramType = "ibd"; }
}
