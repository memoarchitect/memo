// Focused architecture example: a passive manual instrument (needle holder).
// It demonstrates physical decomposition and patient-contact declarations
// without adding functional, logical, or software layers.
package memo_examples_manual_surgical_instrument {
    private import memo::*;
    private import ScalarValues::*;
    private import ModelingMetadata::*;


    part def ManualSurgicalInstrumentSystem specializes memo_architecture_logical_structure::System {
        attribute :>> systemBoundaryDescription = "The manual surgical instrument: the system this example models, with the software and hardware that realize it.";
    }
    // ── Modeled product and physical structure ──────────────────
    part needleHolder : PhysicalAssembly {
        @MemoIdentity { :>> providedId = "MSI-DEV-001"; }
        attribute :>> responsibility = "grasp and drive a suture needle";
    }
    part jawAssembly : MechanicalPart {
        @MemoIdentity { :>> providedId = "MSI-PART-001"; :>> label = "Tungsten carbide jaws"; }
        attribute :>> mechanicalFunction = "serrated needle grip";
        attribute :>> patientContact = true;
        attribute :>> contactNature = "intact tissue / surgical site, indirect";
        attribute :>> contactDuration = "limited (<24 h)";
    }
    part ratchetLock : MechanicalPart {
        @MemoIdentity { :>> providedId = "MSI-PART-002"; }
        attribute :>> mechanicalFunction = "maintains jaw clamping force without continuous grip";
        attribute :>> patientContact = false;
    }
    #refinement dependency needleHolder to jawAssembly;
    #refinement dependency needleHolder to ratchetLock;

    // A task may be traced to the architecture later when the project has a
    // specific allocation or interaction claim to make.
    action taskPlaceSutures : OperativeAction {
        @MemoIdentity { :>> providedId = "MSI-TASK-001"; :>> label = "Place sutures"; }
        attribute :>> taskGoal = "place interrupted sutures";
    }
}
