// Focused example: a ROS 2 mobile logistics robot, modelled with the ROS
// extension. The point of the example is the MECHANISM, not the robot — it
// demonstrates how an extension is used, and it is deliberately the only place
// ROS vocabulary appears outside `extensions/ros`.
//
// Three things it shows:
//   1. Extension types are used exactly like base types. `RosNode` is a
//      `SoftwareComponent`, so period, WCET, safety class and the rest are
//      inherited and every base rule still applies to it.
//   2. ROS communication uses native item definitions/usages, directional
//      ports, interfaces, and flows — no publish/subscribe relation is added.
//   3. Deployment reuses the BASE relations unchanged — `BuildsInto`,
//      `DeploysTo`, `ProvidesEnvironment` — with no ROS-specific relation
//      anywhere in the chain.
package memo_examples_ros_mobile_robot {
    private import memo::*;
    private import ScalarValues::*;
    private import ModelingMetadata::*;

    private import memo_extension_messaging::*;
    private import memo_extension_container::*;
    private import memo_extension_ros::*;

    part def RosMobileRobotSystem specializes memo_architecture_logical_structure::System {
        attribute :>> systemBoundaryDescription = "The ROS mobile robot: the system this example models, with the software and hardware that realize it.";
    }
    // ── Message definitions and named topic instances ──────────────────
    // The definition is the ROS message contract. A named usage is the topic
    // deployed in this system; publisher/subscriber ports reference that same
    // usage and native flows carry its message type.
    item def LaserScan specializes RosMessage {
        attribute :>> rosTypeName = "sensor_msgs/msg/LaserScan";
        attribute :>> messageSchema = "ranges[], intensities[], angle_min, angle_max, scan_time";
    }
    item def VelocityCommand specializes RosMessage {
        attribute :>> rosTypeName = "geometry_msgs/msg/Twist";
        attribute :>> messageSchema = "linear.x, angular.z";
    }
    item def EmergencyStop specializes RosMessage {
        attribute :>> rosTypeName = "std_msgs/msg/Bool";
        attribute :>> messageSchema = "data (true = stop asserted)";
    }

    item topicScan : LaserScan {
        @MemoIdentity { :>> providedId = "RMR-TP-001"; :>> label = "Scan topic"; }
    }
    item topicCmdVel : VelocityCommand {
        @MemoIdentity { :>> providedId = "RMR-TP-002"; :>> label = "Cmd vel topic"; }
    }
    item topicEstop : EmergencyStop {
        @MemoIdentity { :>> providedId = "RMR-TP-003"; :>> label = "Emergency stop topic"; }
    }

    // ── Code ────────────────────────────────────────────────────────────
    part swPerception : SoftwareModule {
        attribute :>> moduleKind = ModuleKind::unit;
        @MemoIdentity { :>> providedId = "RMR-SW-001"; :>> label = "Perception stack"; }
        attribute :>> responsibility = "Lidar driver and obstacle segmentation.";
        attribute :>> safetyClass = SafetyClassKind::B;
    }
    part swNavigation : SoftwareModule {
        attribute :>> moduleKind = ModuleKind::unit;
        @MemoIdentity { :>> providedId = "RMR-SW-002"; :>> label = "Navigation stack"; }
        attribute :>> responsibility = "Global and local planning; velocity command generation.";
        attribute :>> safetyClass = SafetyClassKind::B;
    }
    part swSafety : SoftwareModule {
        attribute :>> moduleKind = ModuleKind::unit;
        @MemoIdentity { :>> providedId = "RMR-SW-003"; :>> label = "Safety monitor"; }
        attribute :>> responsibility = "Independent watchdog: stops the base on obstacle proximity or missing heartbeat.";
        attribute :>> safetyClass = SafetyClassKind::C;
    }

    // ── Nodes ───────────────────────────────────────────────────────────
    //
    // `runtimeKind` is set per node rather than by the type: the first two are
    // composed into one container process, the safety monitor runs as its own
    // process so a fault in navigation cannot take it down. That distinction
    // is exactly what an extension type must NOT decide for the modeller.
    part nodeLidar : RosNode {
        attribute :>> runtimeKind = RuntimeKind::thread;
        @MemoIdentity { :>> providedId = "RMR-ND-001"; :>> label = "LiDAR driver node"; }
        attribute :>> nodeNamespace = "/robot/perception";
        attribute :>> lifecycleManaged = true;
        attribute :>> executorModel = "single-threaded executor, composed";
        attribute :>> periodMs = 50 [milli*s];
        attribute :>> wcetMs = 8 [milli*s];
        attribute :>> safetyClass = SafetyClassKind::B;
        out port scanPublisher : RosPublisher {
            ref :>> topic = topicScan;
            attribute :>> deliverySemantics = MessagingDeliveryKind::atMostOnce;
            attribute :>> publishRateHz = 20 [Hz];
            attribute :>> offeredQos {
                attribute :>> durability = RosDurabilityKind::volatile;
                attribute :>> deadlineMs = 60 [milli*s];
                attribute :>> livelinessLeaseMs = 200 [milli*s];
                attribute :>> historyDepth = 5;
            }
        }
    }
    part nodeNavigation : RosNode {
        attribute :>> runtimeKind = RuntimeKind::thread;
        @MemoIdentity { :>> providedId = "RMR-ND-002"; :>> label = "Navigation node"; }
        attribute :>> nodeNamespace = "/robot/navigation";
        attribute :>> lifecycleManaged = true;
        attribute :>> executorModel = "multi-threaded executor, composed";
        attribute :>> periodMs = 100 [milli*s];
        attribute :>> wcetMs = 35 [milli*s];
        attribute :>> safetyClass = SafetyClassKind::B;
        in port scanSubscriber : RosSubscriber {
            ref :>> topic = topicScan;
            attribute :>> deliverySemantics = MessagingDeliveryKind::atMostOnce;
            attribute :>> lossBehaviour = "hold the last costmap for 200 ms, then command zero velocity";
            attribute :>> requestedQos {
                attribute :>> durability = RosDurabilityKind::volatile;
                attribute :>> deadlineMs = 60 [milli*s];
                attribute :>> livelinessLeaseMs = 200 [milli*s];
                attribute :>> historyDepth = 5;
            }
        }
        out port cmdVelPublisher : RosPublisher {
            ref :>> topic = topicCmdVel;
            attribute :>> deliverySemantics = MessagingDeliveryKind::atLeastOnce;
            attribute :>> publishRateHz = 10 [Hz];
            attribute :>> offeredQos {
                attribute :>> durability = RosDurabilityKind::volatile;
                attribute :>> deadlineMs = 150 [milli*s];
                attribute :>> livelinessLeaseMs = 300 [milli*s];
                attribute :>> historyDepth = 1;
            }
        }
        in port estopSubscriber : RosSubscriber {
            ref :>> topic = topicEstop;
            attribute :>> deliverySemantics = MessagingDeliveryKind::atLeastOnce;
            attribute :>> lossBehaviour = "no publisher within the liveliness lease is treated as stop asserted";
            attribute :>> requestedQos {
                attribute :>> durability = RosDurabilityKind::transientLocal;
                attribute :>> deadlineMs = 100 [milli*s];
                attribute :>> livelinessLeaseMs = 200 [milli*s];
                attribute :>> historyDepth = 1;
            }
        }
        inout port setModeClient : RosServiceClient {
            attribute :>> serviceName = "/robot/safety/set_mode";
        }
        inout port navigateActionServer : RosActionServer {
            attribute :>> actionName = "/robot/navigation/navigate_to_pose";
        }
    }
    part nodeSafetyMonitor : RosNode {
        attribute :>> runtimeKind = RuntimeKind::process;
        @MemoIdentity { :>> providedId = "RMR-ND-003"; :>> label = "Safety monitor node"; }
        attribute :>> nodeNamespace = "/robot/safety";
        attribute :>> lifecycleManaged = false;
        attribute :>> executorModel = "own process, real-time priority";
        attribute :>> periodMs = 20 [milli*s];
        attribute :>> deadlineMs = 20 [milli*s];
        attribute :>> wcetMs = 3 [milli*s];
        attribute :>> priority = 90;
        attribute :>> safetyClass = SafetyClassKind::C;
        attribute :>> faultContainment = "separate process; watchdog-fed; stops the base on its own timeout";
        in port scanSubscriber : RosSubscriber {
            ref :>> topic = topicScan;
            attribute :>> deliverySemantics = MessagingDeliveryKind::atMostOnce;
            attribute :>> lossBehaviour = "two consecutive misses assert the stop";
            attribute :>> requestedQos {
                attribute :>> durability = RosDurabilityKind::volatile;
                attribute :>> deadlineMs = 60 [milli*s];
                attribute :>> livelinessLeaseMs = 200 [milli*s];
                attribute :>> historyDepth = 5;
            }
        }
        in port cmdVelSubscriber : RosSubscriber {
            ref :>> topic = topicCmdVel;
            attribute :>> deliverySemantics = MessagingDeliveryKind::atLeastOnce;
            attribute :>> lossBehaviour = "missing velocity commands assert the stop";
            attribute :>> requestedQos {
                attribute :>> durability = RosDurabilityKind::volatile;
                attribute :>> deadlineMs = 150 [milli*s];
                attribute :>> livelinessLeaseMs = 300 [milli*s];
                attribute :>> historyDepth = 1;
            }
        }
        out port estopPublisher : RosPublisher {
            ref :>> topic = topicEstop;
            attribute :>> deliverySemantics = MessagingDeliveryKind::atLeastOnce;
            attribute :>> publishRateHz = 50 [Hz];
            attribute :>> offeredQos {
                attribute :>> durability = RosDurabilityKind::transientLocal;
                attribute :>> deadlineMs = 100 [milli*s];
                attribute :>> livelinessLeaseMs = 200 [milli*s];
                attribute :>> historyDepth = 1;
            }
        }
        inout port setModeServer : RosServiceServer {
            attribute :>> serviceName = "/robot/safety/set_mode";
        }
        inout port navigateActionClient : RosActionClient {
            attribute :>> actionName = "/robot/navigation/navigate_to_pose";
        }
    }

    // Cross-view mappings: SEI module-view implementation units are distinct
    // from component-and-connector runtime elements. A runtime node realizes
    // the module whose code it executes; it is not the same model element.
    #refinement dependency nodeLidar to swPerception;
    #refinement dependency nodeNavigation to swNavigation;
    #refinement dependency nodeSafetyMonitor to swSafety;

    // ── Native topic, service, and action interfaces ───────────────────
    interface scanToNavigation : RosTopicInterface
        connect nodeLidar.scanPublisher to nodeNavigation.scanSubscriber {
        attribute :>> direction = DirectionKind::output;
    }
    interface scanToSafety : RosTopicInterface
        connect nodeLidar.scanPublisher to nodeSafetyMonitor.scanSubscriber {
        attribute :>> direction = DirectionKind::output;
    }
    interface cmdVelToSafety : RosTopicInterface
        connect nodeNavigation.cmdVelPublisher to nodeSafetyMonitor.cmdVelSubscriber {
        attribute :>> direction = DirectionKind::output;
    }
    interface estopToNavigation : RosTopicInterface
        connect nodeSafetyMonitor.estopPublisher to nodeNavigation.estopSubscriber {
        attribute :>> direction = DirectionKind::output;
    }


    interface setModeService : RosServiceInterface
        connect nodeNavigation.setModeClient to nodeSafetyMonitor.setModeServer {
        attribute :>> direction = DirectionKind::inputOutput;
        attribute :>> timeoutMs = 500 [milli*s];
    }
    interface navigateAction : RosActionInterface
        connect nodeSafetyMonitor.navigateActionClient to nodeNavigation.navigateActionServer {
        attribute :>> direction = DirectionKind::inputOutput;
    }

    // ── Deployment: base relations, unchanged ───────────────────────────
    part imageRuntime : RosContainerImage {
        @MemoIdentity { :>> providedId = "RMR-DU-001"; :>> label = "Robot runtime image"; }
        attribute :>> unitKind = "OCI container image";
        attribute :>> imageReference = "registry.example.com/robot-runtime:2.3.0";
        attribute :>> registry = "registry.example.com";
        attribute :>> digest = "sha256:9f2c1ad4e0b7";
        attribute :>> baseImage = "ros:jazzy-ros-base";
        attribute :>> rosDistribution = "jazzy";
        attribute :>> workspaceOverlay = "/opt/robot_ws";
        attribute :>> integrityProtection = "image signature + SBOM attestation";
    }
    part imageSafety : RosContainerImage {
        @MemoIdentity { :>> providedId = "RMR-DU-002"; :>> label = "Safety monitor image"; }
        attribute :>> unitKind = "OCI container image";
        attribute :>> imageReference = "registry.example.com/safety-monitor:2.3.0";
        attribute :>> registry = "registry.example.com";
        attribute :>> digest = "sha256:41bb7c0e5d92";
        attribute :>> baseImage = "ros:jazzy-ros-core";
        attribute :>> rosDistribution = "jazzy";
        attribute :>> workspaceOverlay = "/opt/safety_ws";
        attribute :>> integrityProtection = "image signature + SBOM attestation";
    }
    allocation : BuildsInto allocate swPerception to imageRuntime;
    allocation : BuildsInto allocate swNavigation to imageRuntime;
    allocation : BuildsInto allocate swSafety to imageSafety;

    part nodeComputeUnit : ProcessingNode {
        @MemoIdentity { :>> providedId = "RMR-HW-001"; :>> label = "Onboard compute unit"; }
        attribute :>> nodeKind = ProcessingNodeKind::SoC;
        attribute :>> processorArchitecture = "arm64, 8 core";
        attribute :>> memoryMB = 16384 [mega*B];
        attribute :>> operatingSystem = "Linux with PREEMPT_RT";
        attribute :>> supportsContainerization = true;
        attribute :>> realTimeCapable = true;
    }
    allocation runtimeImageDeployment : DeploysTo allocate imageRuntime to nodeComputeUnit {
        attribute :>> deploymentKind = DeploymentKind::containerized;
    }
    allocation safetyImageDeployment : DeploysTo allocate imageSafety to nodeComputeUnit {
        attribute :>> deploymentKind = DeploymentKind::containerized;
    }

    part rosRuntime : RosContainerRuntime {
        @MemoIdentity { :>> providedId = "RMR-RT-001"; :>> label = "Onboard ROS runtime"; }
        attribute :>> environmentKind = "container runtime";
        attribute :>> osOrRtos = "Linux with PREEMPT_RT";
        attribute :>> orchestrationPlatform = "systemd-managed compose, no cluster orchestrator";
        attribute :>> runtimeEngine = "containerd";
        attribute :>> rosDistribution = "jazzy";
        attribute :>> rmwImplementation = "rmw_cyclonedds_cpp";
        // Fixed per robot. Two robots sharing a domain would see each other's
        // topics, which is a hazard on a shared network and is visible in no
        // single node.
        attribute :>> rosDomainId = 42;
    }
    connection : ProvidesEnvironment connect nodeComputeUnit to rosRuntime;
    // Illustrative: authored for this example, not the record of a real evaluation.
    verification vcAuthoredSwSafety : VerificationCase {
        @MemoIdentity { :>> providedId = "RMR-VC-A01"; :>> label = "Verify safety monitor"; }
        attribute :>> methodKind = MemoVerificationMethodKind::test;
        attribute :>> acceptanceCriteria = "unit, integration and system tests of 'Safety monitor' with the coverage IEC 62304 requires for software safety class C";
        subject verified : Base::Anything[*] = (swSafety);
    }
    // Illustrative: authored for this example, not the record of a real test run.
    part evAuthoredVcAuthoredSwSafety : MemoEvidence {
        attribute :>> evidenceKind = EvidenceKind::evidence;
        @MemoIdentity { :>> providedId = "RMR-EV-A01"; :>> label = "Verify safety monitor report"; }
        attribute :>> evidenceType = "test report";
        attribute :>> resultSummary = "Illustrative result: the acceptance criteria are met.";
    }
    connection : ProducesEvidence connect vcAuthoredSwSafety to evAuthoredVcAuthoredSwSafety;
    // Illustrative: authored for this example.
    requirement reqAuthoredSwPerception : Requirement {
        attribute :>> requirementType = RequirementTypeKind::system;
        @MemoIdentity { :>> providedId = "RMR-REQ-A01"; :>> label = "Perception stack requirement"; }
        doc /* The software item PerceptionStack shall perform the function allocated to it in the software architecture. */
        attribute :>> status = ElementStatusKind::draft;
    }
    satisfy reqAuthoredSwPerception by swPerception;
    // Illustrative: authored for this example.
    requirement reqAuthoredSwNavigation : Requirement {
        attribute :>> requirementType = RequirementTypeKind::system;
        @MemoIdentity { :>> providedId = "RMR-REQ-A02"; :>> label = "Navigation stack requirement"; }
        doc /* The software item NavigationStack shall perform the function allocated to it in the software architecture. */
        attribute :>> status = ElementStatusKind::draft;
    }
    satisfy reqAuthoredSwNavigation by swNavigation;
    // Illustrative: authored for this example.
    requirement reqAuthoredSwSafety : Requirement {
        attribute :>> requirementType = RequirementTypeKind::system;
        @MemoIdentity { :>> providedId = "RMR-REQ-A03"; :>> label = "Safety monitor requirement"; }
        doc /* The software item SafetyMonitor shall perform the function allocated to it in the software architecture. */
        attribute :>> status = ElementStatusKind::draft;
    }
    satisfy reqAuthoredSwSafety by swSafety;
    // Illustrative: authored for this example.
    requirement needAuthoredSafeOperation : Need {
        attribute :>> needKind = NeedKind::'stakeholder';
        @MemoIdentity { :>> providedId = "RMR-NEED-A01"; :>> label = "Safe operation"; }
        doc /* The device shall operate safely and as intended. */
        attribute :>> priority = "high";
    }
    connection : DerivesFrom connect needAuthoredSafeOperation to reqAuthoredSwPerception;
    connection : DerivesFrom connect needAuthoredSafeOperation to reqAuthoredSwNavigation;
    connection : DerivesFrom connect needAuthoredSafeOperation to reqAuthoredSwSafety;
}
