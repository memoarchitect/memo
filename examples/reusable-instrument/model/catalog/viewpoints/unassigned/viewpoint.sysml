// unassigned viewpoint.
//
// This project does not define its own viewpoint here; it binds the reusable
// MEMO viewpoint that frames these concerns. The views it governs sit beneath
// `views/`.
package memo_examples_reusable_instrument_viewpoints_unassigned {
    // The reusable package declaring unassigned could not be resolved during
    // conversion. Import it here so the views beneath this viewpoint resolve.
}
