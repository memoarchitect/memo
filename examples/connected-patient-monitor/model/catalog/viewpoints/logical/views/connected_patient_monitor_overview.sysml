package memo_examples_connected_patient_monitor_viewpoints_logical_views_connected_patient_monitor_overview {
    private import memo::*;
    private import memo_examples_connected_patient_monitor::*;
    view connectedPatientMonitorOverview : MemoDiagramView { expose memo_examples_connected_patient_monitor::*; attribute depth = 2; attribute :>> viewKind = DiagramViewKind::interconnection; attribute :>> diagramType = "ibd"; ref :>> viewpointDefinition = logicalArchitectureViewpoint; }
}
