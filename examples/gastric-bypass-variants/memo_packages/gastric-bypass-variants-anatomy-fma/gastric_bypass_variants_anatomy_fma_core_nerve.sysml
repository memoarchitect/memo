// GENERATED by `memo anatomy generate` from the Foundational Model of Anatomy (FMA) 5.1.0,
// University of Washington Structural Informatics Group, http://purl.org/sig/ont/fma.owl, CC BY 4.0, https://creativecommons.org/licenses/by/4.0/.
// Converted from OWL to SysML v2 by MEMO's anatomy extension. Do not edit: change the project's AnatomySelectors and regenerate.
package gastric_bypass_variants_anatomy_fma_core_nerve {
    private import gastric_bypass_variants_anatomy_fma::*;
    part def <fma52570> BranchOfCranialNerve :> Nerve;

    part def <fma65132> Nerve :> SegmentOfNeuralTreeOrgan {
        doc /* Segment of neural tree organ which has as its parts a nerve trunk and its branches; together with other nerves of the same tree it constitutes a neural tree. Examples: chorda tympani, digastric branch of facial nerve, greater petrosal nerve, posterior cutaneous branch of posterior ramus of cervical nerve, superior lateral cutaneous nerve of arm. */
    }
}
