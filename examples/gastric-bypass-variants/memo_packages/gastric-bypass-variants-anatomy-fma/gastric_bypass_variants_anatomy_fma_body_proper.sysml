// GENERATED by `memo anatomy generate` from the Foundational Model of Anatomy (FMA) 5.1.0,
// University of Washington Structural Informatics Group, http://purl.org/sig/ont/fma.owl, CC BY 4.0, https://creativecommons.org/licenses/by/4.0/.
// Converted from OWL to SysML v2 by MEMO's anatomy extension. Do not edit: change the project's AnatomySelectors and regenerate.
package gastric_bypass_variants_anatomy_fma_body_proper {
    private import gastric_bypass_variants_anatomy_fma::*;
    part def <fma12266> AbdominalCavity :> BodyCavitySubdivision;
    part def <fma71094> C6PartOfLeftLongusColli :> C6PartOfLongusColli;
    part def <fma71092> C6PartOfLongusColli :> ZoneOfLongusColli;
    part def <fma71093> C6PartOfRightLongusColli :> C6PartOfLongusColli;
    part def <fma71091> C7PartOfLeftLongusColli :> C7PartOfLongusColli;
    part def <fma71089> C7PartOfLongusColli :> ZoneOfLongusColli;
    part def <fma71090> C7PartOfRightLongusColli :> C7PartOfLongusColli;

    part def <fma9586> FibrousPericardium :> MembraneOrgan {
        doc /* Membrane organ which is attached to the pericardial sac proper and the central tendon of diaphragm and is continuous with the pretracheal fascia. */
    }
    part def <fma9580> GreaterOmentum :> Omentum;
    part def <fma9845> LeftMediastinalPleura :> MediastinalPleura;
    part def <fma9736> MediastinalPleura :> RegionOfParietalPleura;
    part def <fma14650> Omentum :> OrganSegment;
    part def <fma85014> PosteriorMediastinalSpace :> SubdivisionOfMediastinalSpace;
    part def <fma9844> RightMediastinalPleura :> MediastinalPleura;

    part def <fma7196> Spleen :> HomogeneousOrgan {
        doc /* Homogenous organ the stroma of which subdivides the parenchyma into red and white pulps. */
    }

    part def <fma3951> SubclavianArtery :> SystemicArtery {
        doc /* Systemic artery the trunk of which is continuous with either the trunk of brachiocephalic artery on the right side, or the aorta on the left side. */
    }
    part def <fma85011> SuperiorMediastinalSpace :> SubdivisionOfMediastinalSpace;
    part def <fma71124> T10PartOfThoracicAorta :> SegmentOfThoracicAorta;
    part def <fma71088> T1PartOfLeftLongusColli :> T1PartOfLongusColli;
    part def <fma71086> T1PartOfLongusColli :> ZoneOfLongusColli;
    part def <fma71087> T1PartOfRightLongusColli :> T1PartOfLongusColli;
    part def <fma71083> T5PartOfThoracicAorta :> SegmentOfThoracicAorta;
    part def <fma68047> T6PartOfThoracicAorta :> SegmentOfThoracicAorta;
    part def <fma71053> T7PartOfFibrousPericardium :> ZoneOfFibrousPericardium;
    part def <fma68048> T7PartOfThoracicAorta :> SegmentOfThoracicAorta;
    part def <fma71049> T8PartOfFibrousPericardium :> ZoneOfFibrousPericardium;
    part def <fma68049> T8PartOfThoracicAorta :> SegmentOfThoracicAorta;
    part def <fma71050> T9PartOfFibrousPericardium :> ZoneOfFibrousPericardium;
    part def <fma68050> T9PartOfThoracicAorta :> SegmentOfThoracicAorta;
    part def <fma3786> ThoracicAorta :> SegmentOfAorta;
}
