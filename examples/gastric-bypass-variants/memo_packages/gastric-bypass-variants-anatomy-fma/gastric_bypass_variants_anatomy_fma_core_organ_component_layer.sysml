// GENERATED by `memo anatomy generate` from the Foundational Model of Anatomy (FMA) 5.1.0,
// University of Washington Structural Informatics Group, http://purl.org/sig/ont/fma.owl, CC BY 4.0, https://creativecommons.org/licenses/by/4.0/.
// Converted from OWL to SysML v2 by MEMO's anatomy extension. Do not edit: change the project's AnatomySelectors and regenerate.
package gastric_bypass_variants_anatomy_fma_core_organ_component_layer {
    private import gastric_bypass_variants_anatomy_fma::*;

    part def <fma45635> Adventitia :> OrganComponentLayer {
        doc /* Organ component layer, each instance of which is the outermost connective tissue layer of some organ or organ part. */
    }
    part def <fma85420> AdventitiaOfOrgan :> Adventitia;
    part def <fma85421> AdventitiaOfOrganRegion :> Adventitia;
    part def <fma63054> AdventitiaOfSegmentOfEsophagus :> AdventitiaOfOrganRegion;
    part def <fma83570> CircularMuscleLayerOfSegmentOfEsophagus :> InnerMuscleLayerOfOrganRegion;
    part def <fma83572> CircularMuscleLayerOfZoneOfSmallIntestine :> InnerMuscleLayerOfOrganRegion;
    part def <fma83571> CircularMuscleLayerOfZoneOfStomach :> InnerMuscleLayerOfOrganRegion;
    part def <fma62899> InnerMuscleLayer :> SubdivisionOfMuscleLayer;
    part def <fma85405> InnerMuscleLayerOfOrgan :> InnerMuscleLayer;
    part def <fma85406> InnerMuscleLayerOfOrganRegion :> InnerMuscleLayer;
    part def <fma62517> LaminaPropria :> OrganComponentLayer;
    part def <fma83560> LaminaPropriaOfZoneOfSmallIntestine :> LaminaPropria;
    part def <fma83567> LongitudinalMuscleLayerOfSegmentOfEsophagus :> OuterMuscleLayerOfOrganRegion;
    part def <fma83569> LongitudinalMuscleLayerOfZoneOfSmallIntestine :> OuterMuscleLayerOfOrganRegion;
    part def <fma83568> LongitudinalMuscleLayerOfZoneOfStomach :> OuterMuscleLayerOfOrganRegion;
    part def <fma83565> MiddleMuscleLayer :> SubdivisionOfMuscleLayer;
    part def <fma85407> MiddleMuscleLayerOfOrgan :> MiddleMuscleLayer;
    part def <fma85408> MiddleMuscleLayerOfOrganRegion :> MiddleMuscleLayer;
    part def <fma85409> MiddleMuscleLayerOfZoneOfStomach :> MiddleMuscleLayerOfOrganRegion;

    part def <fma85355> Mucosa :> OrganComponentLayer {
        doc /* Organ component layer, each instance of which is lining the internal side of some organ. */
    }

    part def <fma82485> OrganComponentLayer :> OrganComponent {
        doc /* Organ component which is a part of a wall of an organ or a membranous layer of an organ. */
    }
    part def <fma62900> OuterMuscleLayer :> SubdivisionOfMuscleLayer;
    part def <fma85410> OuterMuscleLayerOfOrgan :> OuterMuscleLayer;
    part def <fma85411> OuterMuscleLayerOfOrganRegion :> OuterMuscleLayer;

    part def <fma45637> Serosa :> OrganComponentLayer {
        doc /* Organ component layer that constitutes the outermost layer of an organ. */
    }
    part def <fma85423> SerosaOfOrgan :> Serosa;
    part def <fma83563> SubdivisionOfMuscleLayer :> OrganComponentLayer;

    part def <fma85391> Submucosa :> OrganComponentLayer {
        doc /* Organ component layer adjacent to mucosa. */
    }

    part def <fma45636> Subserosa :> OrganComponentLayer {
        doc /* Organ component layer adjacent to serosa of organ. */
    }
    part def <fma85412> SubserosaOfOrgan :> Subserosa;
}
