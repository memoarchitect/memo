// GENERATED by `memo anatomy generate` from the Foundational Model of Anatomy (FMA) 5.1.0,
// University of Washington Structural Informatics Group, http://purl.org/sig/ont/fma.owl, CC BY 4.0, https://creativecommons.org/licenses/by/4.0/.
// Converted from OWL to SysML v2 by MEMO's anatomy extension. Do not edit: change the project's AnatomySelectors and regenerate.
package gastric_bypass_variants_anatomy_fma_alimentary {
    private import gastric_bypass_variants_anatomy_fma::*;

    part def <fma9397> AbdominalPartOfEsophagus :> SegmentOfEsophagus {
        ref part inferiorToThoracicPartOfEsophagus : ThoracicPartOfEsophagus[1..*] :> inferiorToFeatures;
        ref part lymphaticDrainageGastricLymphaticChain : GastricLymphaticChain[1..*] :> lymphaticDrainageFeatures;
        part t10SegmentProperOfEsophagus : T10SegmentProperOfEsophagus[1..*] :> regionalPartFeatures;
        part esophagealSegmentOfEsophagogastricJunction : EsophagealSegmentOfEsophagogastricJunction[1..*] :> regionalPartFeatures;
        part lumenOfAbdominalPartOfEsophagus : LumenOfAbdominalPartOfEsophagus[1..*] :> constitutionalPartFeatures;
        ref part continuousWithCardiaOfStomach : CardiaOfStomach[1..*] :> continuousWithFeatures;
        ref part containedInLeftPosteriorSubphrenicSpace : LeftPosteriorSubphrenicSpace[1..*] :> containedInFeatures;
        part wallOfAbdominalPartOfEsophagus : WallOfAbdominalPartOfEsophagus[1..*] :> constitutionalPartFeatures;
        ref part lymphaticDrainageSuperiorPartOfLeftGastricLymphaticChain : SuperiorPartOfLeftGastricLymphaticChain[1..*] :> lymphaticDrainageFeatures;
        ref part lymphaticDrainageParacardialPartOfLeftGastricLymphaticChain : ParacardialPartOfLeftGastricLymphaticChain[1..*] :> lymphaticDrainageFeatures;
        ref part lymphaticDrainageLeftGastricLymphaticChain : LeftGastricLymphaticChain[1..*] :> lymphaticDrainageFeatures;
        ref part continuousWithThoracicPartOfEsophagus : ThoracicPartOfEsophagus[1..*] :> continuousWithFeatures;
        ref part lymphaticDrainageInferiorPartOfLeftGastricLymphaticChain : InferiorPartOfLeftGastricLymphaticChain[1..*] :> lymphaticDrainageFeatures;
        ref part superiorToCardiaOfStomach : CardiaOfStomach[1..*] :> superiorToFeatures;
    }
    part def <fma63055> AdventitiaOfCervicalPartOfEsophagus :> AdventitiaOfSegmentOfEsophagus;

    part def <fma63006> AdventitiaOfEsophagus :> AdventitiaOfOrgan {
        part adventitiaOfCervicalPartOfEsophagus : AdventitiaOfCervicalPartOfEsophagus[1..*] :> regionalPartFeatures;
        part adventitiaOfThoracicPartOfEsophagus : AdventitiaOfThoracicPartOfEsophagus[1..*] :> regionalPartFeatures;
        part denseIrregularConnectiveTissueOfAdventitiaOfEsophagus : DenseIrregularConnectiveTissueOfAdventitiaOfEsophagus[1..*] :> constitutionalPartFeatures;
    }
    part def <fma63056> AdventitiaOfThoracicPartOfEsophagus :> AdventitiaOfSegmentOfEsophagus;
    part def <fma17414> AnteriorWallOfAscendingPartOfDuodenum :> RegionOfWallOfDuodenum_fma86109;

    part def <fma17399> AnteriorWallOfBodyOfStomach :> AnteriorWallOfZoneOfStomach {
        part internalSurfaceOfAnteriorWallOfBodyOfStomach : InternalSurfaceOfAnteriorWallOfBodyOfStomach[1..*] :> regionalPartFeatures;
    }
    part def <fma17433> AnteriorWallOfCardiaOfStomach :> AnteriorWallOfZoneOfStomach;
    part def <fma17412> AnteriorWallOfDescendingPartOfDuodenum :> RegionOfWallOfDuodenum_fma86109;
    part def <fma86664> AnteriorWallOfDistalPartOfJejunum :> RegionOfWallOfJejunum;

    part def <fma17407> AnteriorWallOfDuodenum :> RegionOfWallOfDuodenum_fma86109 {
        part submucosaOfAnteriorWallOfDuodenum : SubmucosaOfAnteriorWallOfDuodenum[1..*] :> constitutionalPartFeatures;
    }

    part def <fma17398> AnteriorWallOfFundusOfStomach :> AnteriorWallOfZoneOfStomach {
        part internalSurfaceOfAnteriorWallOfFundusOfStomach : InternalSurfaceOfAnteriorWallOfFundusOfStomach[1..*] :> regionalPartFeatures;
    }
    part def <fma17413> AnteriorWallOfHorizontalPartOfDuodenum :> RegionOfWallOfDuodenum_fma86109;
    part def <fma86662> AnteriorWallOfMiddlePartOfJejunum :> RegionOfWallOfJejunum;
    part def <fma86660> AnteriorWallOfProximalPartOfJejunum :> RegionOfWallOfJejunum;

    part def <fma17400> AnteriorWallOfPyloricAntrum :> AnteriorWallOfZoneOfStomach {
        part internalSurfaceOfAnteriorWallOfPyloricAntrum : InternalSurfaceOfAnteriorWallOfPyloricAntrum[1..*] :> regionalPartFeatures;
    }

    part def <fma17401> AnteriorWallOfPyloricCanal :> AnteriorWallOfZoneOfStomach {
        part internalSurfaceOfAnteriorWallOfPyloricCanal : InternalSurfaceOfAnteriorWallOfPyloricCanal[1..*] :> regionalPartFeatures;
    }
    part def <fma17434> AnteriorWallOfPylorus :> AnteriorWallOfZoneOfStomach;

    part def <fma14583> AnteriorWallOfStomach :> RegionOfWallOfStomach {
        part internalSurfaceOfAnteriorWallOfStomach : InternalSurfaceOfAnteriorWallOfStomach[1..*] :> regionalPartFeatures;
    }
    part def <fma17411> AnteriorWallOfSuperiorPartOfDuodenum :> RegionOfWallOfDuodenum_fma86109;
    part def <fma263718> AreolarConnectiveTissueOfCircularMuscleLayerOfDuodenum :> AreolarConnectiveTissue;
    part def <fma263710> AreolarConnectiveTissueOfLaminaPropriaOfStomach :> AreolarConnectiveTissue;
    part def <fma263720> AreolarConnectiveTissueOfLongitudinalMuscleLayerOfDuodenum :> AreolarConnectiveTissue;
    part def <fma263716> AreolarConnectiveTissueOfSubmucosaOfDuodenum :> AreolarConnectiveTissue;

    part def <fma14930> AscendingPartOfDuodenum :> SegmentOfDuodenum {
        part lumenOfAscendingPartOfDuodenum : LumenOfAscendingPartOfDuodenum[1..*] :> constitutionalPartFeatures;
        part wallOfAscendingPartOfDuodenum : WallOfAscendingPartOfDuodenum[1..*] :> constitutionalPartFeatures;
        part ascendingPartProperOfDuodenum : AscendingPartProperOfDuodenum[1..*] :> regionalPartFeatures;
        part duodenojejunalJunction : DuodenojejunalJunction[1..*] :> regionalPartFeatures;
    }
    part def <fma86726> AscendingPartProperOfDuodenum :> ZoneOfDuodenum;
    part def <fma261347> BasementMembraneOfEpitheliumProperOfEsophagus :> BasementMembrane;

    part def <fma14560> BodyOfStomach :> ZoneOfStomach {
        part wallOfBodyOfStomach : WallOfBodyOfStomach[1..*] :> constitutionalPartFeatures;
        part prepylorus : Prepylorus[1..*] :> regionalPartFeatures;
        part bodyProperOfStomach : BodyProperOfStomach[1..*] :> regionalPartFeatures;
        ref part continuousWithPyloricPartOfStomach : PyloricPartOfStomach[1..*] :> continuousWithFeatures;
        part lumenOfBodyOfStomach : LumenOfBodyOfStomach[1..*] :> constitutionalPartFeatures;
        ref part continuousWithFundusOfStomach : FundusOfStomach[1..*] :> continuousWithFeatures;
    }
    part def <fma0326833> BodyProperOfStomach :> ZoneOfStomach;

    part def <fma52526> C6SegmentOfEsophagus :> VertebralSegmentOfEsophagus {
        ref part medialToRightRecurrentLaryngealNerve : RightRecurrentLaryngealNerve[1..*] :> medialToFeatures;
        ref part anteriorToC6PartOfRightLongusColli : C6PartOfRightLongusColli[1..*] :> anteriorToFeatures;
        ref part posteriorToC6SegmentOfTrachea : C6SegmentOfTrachea[1..*] :> posteriorToFeatures;
        ref part anteriorToC6PartOfLeftLongusColli : C6PartOfLeftLongusColli[1..*] :> anteriorToFeatures;
        ref part anteriorToC6SegmentOfAnteriorLongitudinalLigament : C6SegmentOfAnteriorLongitudinalLigament[1..*] :> anteriorToFeatures;
        part c6SegmentProperOfEsophagus : C6SegmentProperOfEsophagus[1..*] :> regionalPartFeatures;
        ref part directRightOfC6SegmentOfAnteriorLongitudinalLigament : C6SegmentOfAnteriorLongitudinalLigament[1..*] :> directRightOfFeatures;
        ref part directRightOfC6SegmentOfTrachea : C6SegmentOfTrachea[1..*] :> directRightOfFeatures;
        ref part directLeftOfC6SegmentOfTrachea : C6SegmentOfTrachea[1..*] :> directLeftOfFeatures;
        ref part directRightOfC6PartOfLeftLongusColli : C6PartOfLeftLongusColli[1..*] :> directRightOfFeatures;
        ref part medialToLeftRecurrentLaryngealNerve : LeftRecurrentLaryngealNerve[1..*] :> medialToFeatures;
        part esophagealSegmentOfPharyngoesophagealJunction : EsophagealSegmentOfPharyngoesophagealJunction[1..*] :> regionalPartFeatures;
        ref part directLeftOfC6SegmentOfAnteriorLongitudinalLigament : C6SegmentOfAnteriorLongitudinalLigament[1..*] :> directLeftOfFeatures;
        ref part directRightOfLeftRecurrentLaryngealNerve : LeftRecurrentLaryngealNerve[1..*] :> directRightOfFeatures;
        ref part directLeftOfC6PartOfRightLongusColli : C6PartOfRightLongusColli[1..*] :> directLeftOfFeatures;
        ref part directLeftOfRightRecurrentLaryngealNerve : RightRecurrentLaryngealNerve[1..*] :> directLeftOfFeatures;
    }
    part def <fma255840> C6SegmentProperOfEsophagus :> SubdivisionOfVertebralSegmentOfEsophagus;

    part def <fma52528> C7SegmentOfEsophagus :> VertebralSegmentOfEsophagus {
        ref part posteriorToC7SegmentOfTrachea : C7SegmentOfTrachea[1..*] :> posteriorToFeatures;
        ref part anteriorToC7PartOfLeftLongusColli : C7PartOfLeftLongusColli[1..*] :> anteriorToFeatures;
        ref part directLeftOfRightRecurrentLaryngealNerve : RightRecurrentLaryngealNerve[1..*] :> directLeftOfFeatures;
        ref part directRightOfLeftRecurrentLaryngealNerve : LeftRecurrentLaryngealNerve[1..*] :> directRightOfFeatures;
        ref part directLeftOfC7PartOfRightLongusColli : C7PartOfRightLongusColli[1..*] :> directLeftOfFeatures;
        ref part posteriorToRightRecurrentLaryngealNerve : RightRecurrentLaryngealNerve[1..*] :> posteriorToFeatures;
        ref part anteriorToC7PartOfRightLongusColli : C7PartOfRightLongusColli[1..*] :> anteriorToFeatures;
        ref part directLeftOfC7SegmentOfTrachea : C7SegmentOfTrachea[1..*] :> directLeftOfFeatures;
        ref part directRightOfC7SegmentOfAnteriorLongitudinalLigament : C7SegmentOfAnteriorLongitudinalLigament[1..*] :> directRightOfFeatures;
        ref part directLeftOfC7SegmentOfAnteriorLongitudinalLigament : C7SegmentOfAnteriorLongitudinalLigament[1..*] :> directLeftOfFeatures;
        ref part directRightOfC7SegmentOfTrachea : C7SegmentOfTrachea[1..*] :> directRightOfFeatures;
        ref part posteriorToLeftRecurrentLaryngealNerve : LeftRecurrentLaryngealNerve[1..*] :> posteriorToFeatures;
        ref part anteriorToC7SegmentOfAnteriorLongitudinalLigament : C7SegmentOfAnteriorLongitudinalLigament[1..*] :> anteriorToFeatures;
        ref part directRightOfC7PartOfLeftLongusColli : C7PartOfLeftLongusColli[1..*] :> directRightOfFeatures;
    }
    part def <fma280989> CapillaryNetworkOfOrganComponent :> SystemicCapillaryNetworkOfCardinalOrganPart;
    part def <fma45633> CapillaryPlexus :> SegmentOfBloodVesselTreeOrgan;

    part def <fma63076> CardiacEsophagealGland :> EsophagealGland {
        part lumenOfEsophagealGland : LumenOfEsophagealGland[1..*] :> constitutionalPartFeatures;
        part epitheliumOfEsophagealGland : EpitheliumOfEsophagealGland[1..*] :> constitutionalPartFeatures;
    }

    part def <fma14561> CardiaOfStomach :> ZoneOfStomach {
        ref part lymphaticDrainageParacardialPartOfLeftGastricLymphaticChain : ParacardialPartOfLeftGastricLymphaticChain[1..*] :> lymphaticDrainageFeatures;
        part lumenOfCardiaOfStomach : LumenOfCardiaOfStomach[1..*] :> constitutionalPartFeatures;
        part wallOfCardiaOfStomach : WallOfCardiaOfStomach[1..*] :> constitutionalPartFeatures;
        ref part lymphaticDrainageDiaphragmaticLymphaticChain : DiaphragmaticLymphaticChain[1..*] :> lymphaticDrainageFeatures;
        ref part lymphaticDrainageLeftGastricLymphaticChain : LeftGastricLymphaticChain[1..*] :> lymphaticDrainageFeatures;
        ref part lymphaticDrainageGastricLymphaticChain : GastricLymphaticChain[1..*] :> lymphaticDrainageFeatures;
        ref part continuousWithFundusOfStomach : FundusOfStomach[1..*] :> continuousWithFeatures;
        ref part continuousWithAbdominalPartOfEsophagus : AbdominalPartOfEsophagus[1..*] :> continuousWithFeatures;
        ref part lymphaticDrainageSuperiorPartOfLeftGastricLymphaticChain : SuperiorPartOfLeftGastricLymphaticChain[1..*] :> lymphaticDrainageFeatures;
    }

    part def <fma14585> CavityOfStomach :> OrganCavity {
        doc /* Organ cavity which is bound by the internal surface of the wall of stomach. Examples: There is only one cavity of stomach. */
        ref part continuousWithLumenOfEsophagus : LumenOfEsophagus[1..*] :> continuousWithFeatures;
        ref part continuousWithLumenOfSmallIntestine : LumenOfSmallIntestine[1..*] :> continuousWithFeatures;
    }

    part def <fma9395> CervicalPartOfEsophagus :> SegmentOfEsophagus {
        ref part lymphaticDrainageLeftRetropharyngealLymphaticChain : LeftRetropharyngealLymphaticChain[1..*] :> lymphaticDrainageFeatures;
        ref part lymphaticDrainageRightParatrachealLymphaticChain : RightParatrachealLymphaticChain[1..*] :> lymphaticDrainageFeatures;
        part lumenOfCervicalPartOfEsophagus : LumenOfCervicalPartOfEsophagus[1..*] :> constitutionalPartFeatures;
        part c7SegmentOfEsophagus : C7SegmentOfEsophagus[1..*] :> regionalPartFeatures;
        ref part lymphaticDrainageRightRetropharyngealLymphaticChain : RightRetropharyngealLymphaticChain[1..*] :> lymphaticDrainageFeatures;
        part c6SegmentOfEsophagus : C6SegmentOfEsophagus[1..*] :> regionalPartFeatures;
        ref part lymphaticDrainageLeftParatrachealLymphaticChain : LeftParatrachealLymphaticChain[1..*] :> lymphaticDrainageFeatures;
        ref part continuousWithOropharynx : Oropharynx[1..*] :> continuousWithFeatures;
        part wallOfCervicalPartOfEsophagus : WallOfCervicalPartOfEsophagus[1..*] :> constitutionalPartFeatures;
        ref part lymphaticDrainageAnteriorDeepCervicalLymphaticChain : AnteriorDeepCervicalLymphaticChain[1..*] :> lymphaticDrainageFeatures;
        ref part containedInSpaceOfAnteriorCompartmentOfNeck : SpaceOfAnteriorCompartmentOfNeck[1..*] :> containedInFeatures;
        ref part superiorToThoracicPartOfEsophagus : ThoracicPartOfEsophagus[1..*] :> superiorToFeatures;
        ref part inferiorToOropharynx : Oropharynx[1..*] :> inferiorToFeatures;
        ref part continuousWithThoracicPartOfEsophagus : ThoracicPartOfEsophagus[1..*] :> continuousWithFeatures;
    }

    part def <fma63048> CircularMuscleLayerOfAbdominalPartOfEsophagus :> CircularMuscleLayerOfSegmentOfEsophagus {
        part intercellularMatrixOfCircularMuscleLayerOfAbdominalPartOfEsophagus : IntercellularMatrixOfCircularMuscleLayerOfAbdominalPartOfEsophagus[1..*] :> constitutionalPartFeatures;
    }
    part def <fma17289> CircularMuscleLayerOfBodyOfStomach :> CircularMuscleLayerOfZoneOfStomach;
    part def <fma17478> CircularMuscleLayerOfCardiaOfStomach :> CircularMuscleLayerOfZoneOfStomach;

    part def <fma63044> CircularMuscleLayerOfCervicalPartOfEsophagus :> CircularMuscleLayerOfSegmentOfEsophagus {
        part intercellularMatrixOfCircularMuscleLayerOfCervicalPartOfEsophagus : IntercellularMatrixOfCircularMuscleLayerOfCervicalPartOfEsophagus[1..*] :> constitutionalPartFeatures;
    }

    part def <fma14945> CircularMuscleLayerOfDuodenum :> CircularMuscleLayerOfZoneOfSmallIntestine {
        part smoothMuscleTissueOfCircularMuscleLayerOfDuodenum : SmoothMuscleTissueOfCircularMuscleLayerOfDuodenum[1..*] :> constitutionalPartFeatures;
        part areolarConnectiveTissueOfCircularMuscleLayerOfDuodenum : AreolarConnectiveTissueOfCircularMuscleLayerOfDuodenum[1..*] :> constitutionalPartFeatures;
    }
    part def <fma67605> CircularMuscleLayerOfEsophagus :> InnerMuscleLayerOfOrgan;
    part def <fma17281> CircularMuscleLayerOfFundusOfStomach :> CircularMuscleLayerOfZoneOfStomach;
    part def <fma14952> CircularMuscleLayerOfJejunum :> CircularMuscleLayerOfZoneOfSmallIntestine;
    part def <fma17294> CircularMuscleLayerOfPyloricAntrum :> CircularMuscleLayerOfZoneOfStomach;
    part def <fma17299> CircularMuscleLayerOfPyloricCanal :> CircularMuscleLayerOfZoneOfStomach;
    part def <fma14911> CircularMuscleLayerOfStomach :> InnerMuscleLayerOfOrgan;

    part def <fma63046> CircularMuscleLayerOfThoracicPartOfEsophagus :> CircularMuscleLayerOfSegmentOfEsophagus {
        part intercellularMatrixOfCircularMuscleLayerOfThoracicPartOfEsophagus : IntercellularMatrixOfCircularMuscleLayerOfThoracicPartOfEsophagus[1..*] :> constitutionalPartFeatures;
    }
    part def <fma263486> ConnectiveTissueOfSerosaOfDuodenum :> ConnectiveTissueOfRegionOfVisceralPeritoneum;
    part def <fma263524> ConnectiveTissueOfSerosaOfStomach :> ConnectiveTissueOfRegionOfVisceralPeritoneum;
    part def <fma269063> CryptOfLieberkuhnOfDuodenum :> CryptOfLieberkuhnOfSmallIntestine;
    part def <fma269065> CryptOfLieberkuhnOfJejunum :> CryptOfLieberkuhnOfSmallIntestine;
    part def <fma15693> CryptOfLieberkuhnOfSmallIntestine :> CryptOfLieberkuhn;
    part def <fma263774> DenseIrregularConnectiveTissueOfAdventitiaOfEsophagus :> DenseIrregularConnectiveTissue;
    part def <fma263700> DenseRegularCollagenousTissueOfSubmucosaOfEsophagus :> DenseRegularCollagenousTissue;
    part def <fma263704> DenseRegularElasticTissueOfLaminaPropriaOfEsophagus :> DenseRegularElasticTissue;

    part def <fma14928> DescendingPartOfDuodenum :> SegmentOfDuodenum {
        part wallOfDescendingPartOfDuodenum : WallOfDescendingPartOfDuodenum[1..*] :> constitutionalPartFeatures;
        part lumenOfDescendingPartOfDuodenum : LumenOfDescendingPartOfDuodenum[1..*] :> constitutionalPartFeatures;
    }
    part def <fma62837> DiffuseMucosaAssociatedLymphoidTissue :> MucosaAssociatedLymphoidTissue;

    part def <fma71134> DistalHalfOfDuodenum :> ZoneOfDuodenum {
        ref part developsFromMidgut : Midgut[1..*] :> developsFromFeatures;
    }

    part def <fma16983> DistalPartOfJejunum :> ZoneOfJejunum {
        part lumenOfDistalPartOfJejunum : LumenOfDistalPartOfJejunum[1..*] :> constitutionalPartFeatures;
        part wallOfDistalPartOfJejunum : WallOfDistalPartOfJejunum[1..*] :> constitutionalPartFeatures;
    }
    part def <fma265213> DuodenalBulb :> SegmentOfDuodenum;
    part def <fma17231> DuodenalEpithelium :> EpitheliumOfZoneOfSmallIntestine;

    part def <fma15060> DuodenalGland :> SimpleBranchedTubularGland {
        part epitheliumOfDuodenalGland : EpitheliumOfDuodenalGland[1..*] :> constitutionalPartFeatures;
        part lumenOfDuodenalGland : LumenOfDuodenalGland[1..*] :> constitutionalPartFeatures;
    }
    part def <fma15957> DuodenojejunalJunction :> ZoneOfContinuity;

    part def <fma7206> Duodenum :> SegmentOfSmallIntestine {
        part horizontalPartOfDuodenum : HorizontalPartOfDuodenum[1..*] :> regionalPartFeatures;
        part superiorFlexureOfDuodenum : SuperiorFlexureOfDuodenum[1..*] :> regionalPartFeatures;
        part inferiorFlexureOfDuodenum : InferiorFlexureOfDuodenum[1..*] :> regionalPartFeatures;
        ref part continuousWithJejunum : Jejunum[1..*] :> continuousWithFeatures;
        part lumenOfDuodenum : LumenOfDuodenum[1..*] :> constitutionalPartFeatures;
        part descendingPartOfDuodenum : DescendingPartOfDuodenum[1..*] :> regionalPartFeatures;
        part ascendingPartOfDuodenum : AscendingPartOfDuodenum[1..*] :> regionalPartFeatures;
        part wallOfDuodenum : WallOfDuodenum[1..*] :> constitutionalPartFeatures;
        part distalHalfOfDuodenum : DistalHalfOfDuodenum[1..*] :> regionalPartFeatures;
        ref part lymphaticDrainageHepaticLymphaticChain : HepaticLymphaticChain[1..*] :> lymphaticDrainageFeatures;
        part proximalHalfOfDuodenum : ProximalHalfOfDuodenum[1..*] :> regionalPartFeatures;
        part superiorPartOfDuodenum : SuperiorPartOfDuodenum[1..*] :> regionalPartFeatures;
        ref part continuousWithPyloricPartOfStomach : PyloricPartOfStomach[1..*] :> continuousWithFeatures;
    }
    part def <fma63070> EpitheliumOfAbdominalPartOfEsophagus :> EpitheliumOfZoneOfEsophagus;
    part def <fma17285> EpitheliumOfBodyOfStomach :> EpitheliumOfZoneOfStomach;
    part def <fma17467> EpitheliumOfCardiaOfStomach :> EpitheliumOfZoneOfStomach;
    part def <fma63068> EpitheliumOfCervicalPartOfEsophagus :> EpitheliumOfZoneOfEsophagus;
    part def <fma63242> EpitheliumOfDuodenalGland :> EpitheliumOfGlandOfSmallIntestine;
    part def <fma63238> EpitheliumOfEsophagealGland :> NonkeratinizingStratifiedSquamousEpithelium;

    part def <fma63063> EpitheliumOfEsophagus :> NonkeratinizingStratifiedSquamousEpithelium {
        part stratumSpinosumOfEsophagealEpithelium : StratumSpinosumOfEsophagealEpithelium[1..*] :> constitutionalPartFeatures;
        part epitheliumProperOfEsophagus : EpitheliumProperOfEsophagus[1..*] :> regionalPartFeatures;
        part basementMembraneOfEpitheliumProperOfEsophagus : BasementMembraneOfEpitheliumProperOfEsophagus[1..*] :> constitutionalPartFeatures;
        part epitheliumOfEsophagealGland : EpitheliumOfEsophagealGland[1..*] :> regionalPartFeatures;
        part stratumGerminativumOfEsophagealEpithelium : StratumGerminativumOfEsophagealEpithelium[1..*] :> constitutionalPartFeatures;
        part stratumCorneumOfEsophagealEpithelium : StratumCorneumOfEsophagealEpithelium[1..*] :> constitutionalPartFeatures;
    }
    part def <fma17277> EpitheliumOfFundusOfStomach :> EpitheliumOfZoneOfStomach;
    part def <fma63458> EpitheliumOfGastricGland :> GlandularColumnarEpithelium;
    part def <fma17291> EpitheliumOfPyloricAntrum :> EpitheliumOfZoneOfStomach;
    part def <fma17296> EpitheliumOfPyloricCanal :> EpitheliumOfZoneOfStomach;
    part def <fma17471> EpitheliumOfPylorus :> EpitheliumOfZoneOfStomach;

    part def <fma17091> EpitheliumOfStomach :> MicrovillusColumnarEpithelium {
        part epitheliumProperOfStomach : EpitheliumProperOfStomach[1..*] :> regionalPartFeatures;
        part epitheliumOfGastricGland : EpitheliumOfGastricGland[1..*] :> regionalPartFeatures;
    }
    part def <fma63069> EpitheliumOfThoracicPartOfEsophagus :> EpitheliumOfZoneOfEsophagus;
    part def <fma63075> EpitheliumProperOfEsophagus :> NonkeratinizingStratifiedSquamousEpithelium;
    part def <fma63457> EpitheliumProperOfStomach :> MicrovillusColumnarEpithelium;
    part def <fma255834> EsophagealSegmentOfEsophagogastricJunction :> SegmentOfEsophagus;
    part def <fma255836> EsophagealSegmentOfPharyngoesophagealJunction :> SegmentOfEsophagus;

    part def <fma7131> Esophagus :> OrganWithOrganCavity {
        doc /* Organ with organ cavity, each instance of which is continuous superiorly with some pharynx and inferiorly with some stomach. Examples: There is only one esophagus. */
        ref part adjacentToThoracicAorta : ThoracicAorta[1..*] :> adjacentToFeatures;
        ref part continuousWithStomach : Stomach[1..*] :> continuousWithFeatures;
        part wallOfEsophagus : WallOfEsophagus[1..*] :> constitutionalPartFeatures;
        ref part arterialSupplyEsophagealBranchOfLeftFirstBronchialArtery : EsophagealBranchOfLeftFirstBronchialArtery[1..*] :> arterialSupplyFeatures;
        ref part boundedByExternalSurfaceOfEsophagus : ExternalSurfaceOfEsophagus[1..*] :> boundedByFeatures;
        ref part venousDrainageEsophagealTributaryOfLeftInferiorThyroidVein : EsophagealTributaryOfLeftInferiorThyroidVein[1..*] :> venousDrainageFeatures;
        ref part continuousWithPharynx : Pharynx[1..*] :> continuousWithFeatures;
        ref part venousDrainageEsophagealTributaryOfRightInferiorThyroidVein : EsophagealTributaryOfRightInferiorThyroidVein[1..*] :> venousDrainageFeatures;
        ref part adjacentToTrachea : Trachea[1..*] :> adjacentToFeatures;
        ref part developsFromForegut : Foregut[1..*] :> developsFromFeatures;
        ref part arterialSupplyEsophagealBranchOfLeftSecondBronchialArtery : EsophagealBranchOfLeftSecondBronchialArtery[1..*] :> arterialSupplyFeatures;
        part abdominalPartOfEsophagus : AbdominalPartOfEsophagus[1..*] :> regionalPartFeatures;
        ref part distalToPharynx : Pharynx[1..*] :> distalToFeatures;
        ref part superiorToStomach : Stomach[1..*] :> superiorToFeatures;
        ref part arterialSupplyEsophagealArtery : EsophagealArtery[1..*] :> arterialSupplyFeatures;
        part cervicalPartOfEsophagus : CervicalPartOfEsophagus[1..*] :> regionalPartFeatures;
        ref part arterialSupplyEsophagealBranchOfLateralBranchOfLeftInferiorPhrenicArtery : EsophagealBranchOfLateralBranchOfLeftInferiorPhrenicArtery[1..*] :> arterialSupplyFeatures;
        ref part venousDrainageEsophagealTributaryOfHemiAzygosVein : EsophagealTributaryOfHemiAzygosVein[1..*] :> venousDrainageFeatures;
        ref part venousDrainageEsophagealTributaryOfAzygosVein : EsophagealTributaryOfAzygosVein[1..*] :> venousDrainageFeatures;
        ref part continuousDistallyWithStomach : Stomach[1..*] :> continuousDistallyWithFeatures;
        ref part proximalToStomach : Stomach[1..*] :> proximalToFeatures;
        ref part nerveSupplyPosteriorEsophagealNervePlexus : PosteriorEsophagealNervePlexus[1..*] :> nerveSupplyFeatures;
        ref part adjacentToThoracicVertebralColumn : ThoracicVertebralColumn[1..*] :> adjacentToFeatures;
        ref part boundedByInternalSurfaceOfEsophagus : InternalSurfaceOfEsophagus[1..*] :> boundedByFeatures;
        part thoracicPartOfEsophagus : ThoracicPartOfEsophagus[1..*] :> regionalPartFeatures;
        ref part arterialSupplyEsophagealBranchOfRightBronchialArtery : EsophagealBranchOfRightBronchialArtery[1..*] :> arterialSupplyFeatures;
        part lumenOfEsophagus : LumenOfEsophagus[1..*] :> constitutionalPartFeatures;
        ref part venousDrainageEsophagealTributaryOfLeftGastricVein : EsophagealTributaryOfLeftGastricVein[1..*] :> venousDrainageFeatures;
        ref part nerveSupplyAnteriorEsophagealNervePlexus : AnteriorEsophagealNervePlexus[1..*] :> nerveSupplyFeatures;
        ref part lymphaticDrainageEsophagealTributaryOfThoracicDuct : EsophagealTributaryOfThoracicDuct[1..*] :> lymphaticDrainageFeatures;
        ref part inferiorToPharynx : Pharynx[1..*] :> inferiorToFeatures;
        ref part venousDrainageEsophagealTributaryOfBrachiocephalicVein : EsophagealTributaryOfBrachiocephalicVein[1..*] :> venousDrainageFeatures;
    }

    part def <fma14559> FundusOfStomach :> ZoneOfStomach {
        part lumenOfFundusOfStomach : LumenOfFundusOfStomach[1..*] :> constitutionalPartFeatures;
        ref part lymphaticDrainageRightGastroEpiploicLymphaticChain : RightGastroEpiploicLymphaticChain[1..*] :> lymphaticDrainageFeatures;
        part wallOfFundusOfStomach : WallOfFundusOfStomach[1..*] :> constitutionalPartFeatures;
        ref part continuousWithCardiaOfStomach : CardiaOfStomach[1..*] :> continuousWithFeatures;
        ref part continuousWithBodyOfStomach : BodyOfStomach[1..*] :> continuousWithFeatures;
        ref part lymphaticDrainageGastricLymphaticChain : GastricLymphaticChain[1..*] :> lymphaticDrainageFeatures;
    }
    part def <fma14920> GastricCardiacGland :> GastricGland;
    part def <fma17046> GastroduodenalJunction :> ZoneOfContinuity;
    part def <fma15076> HepatopancreaticAmpulla :> SegmentOfCommonBileDuct;

    part def <fma14929> HorizontalPartOfDuodenum :> SegmentOfDuodenum {
        part wallOfHorizontalPartOfDuodenum : WallOfHorizontalPartOfDuodenum[1..*] :> constitutionalPartFeatures;
        part lumenOfHorizontalPartOfDuodenum : LumenOfHorizontalPartOfDuodenum[1..*] :> constitutionalPartFeatures;
    }
    part def <fma7208> Ileum :> SegmentOfSmallIntestine;
    part def <fma15956> InferiorFlexureOfDuodenum :> FlexureOfDuodenum;
    part def <fma63529> InnerCircularLayerOfMuscularisMucosaeOfStomach :> MuscularisMucosae;
    part def <fma263980> IntercellularMatrixOfCircularMuscleLayerOfAbdominalPartOfEsophagus :> PortionOfExtracellularMatrix;
    part def <fma263984> IntercellularMatrixOfCircularMuscleLayerOfCervicalPartOfEsophagus :> PortionOfExtracellularMatrix;
    part def <fma263982> IntercellularMatrixOfCircularMuscleLayerOfThoracicPartOfEsophagus :> PortionOfExtracellularMatrix;
    part def <fma263968> IntercellularMatrixOfLongitudinalMuscleLayerOfAbdominalPartOfEsophagus :> PortionOfExtracellularMatrix;
    part def <fma263976> IntercellularMatrixOfLongitudinalMuscleLayerOfCervicalPartOfEsophagus :> PortionOfExtracellularMatrix;
    part def <fma263974> IntercellularMatrixOfLongitudinalMuscleLayerOfThoracicPartOfEsophagus :> PortionOfExtracellularMatrix;
    part def <fma263960> IntercellularMatrixOfMuscularisMucosaeOfDuodenum :> PortionOfExtracellularMatrix;
    part def <fma17430> InternalSurfaceOfAnteriorWallOfBodyOfStomach :> InternalSurfaceOfAnteriorWallOfSubdivisionOfStomach;
    part def <fma17429> InternalSurfaceOfAnteriorWallOfFundusOfStomach :> InternalSurfaceOfAnteriorWallOfSubdivisionOfStomach;
    part def <fma17431> InternalSurfaceOfAnteriorWallOfPyloricAntrum :> InternalSurfaceOfAnteriorWallOfSubdivisionOfStomach;
    part def <fma17432> InternalSurfaceOfAnteriorWallOfPyloricCanal :> InternalSurfaceOfAnteriorWallOfSubdivisionOfStomach;
    part def <fma17424> InternalSurfaceOfAnteriorWallOfStomach :> InternalSurfaceOfSubdivisionOfStomach;
    part def <fma17441> InternalSurfaceOfPosteriorWallOfBodyOfStomach :> InternalSurfaceOfPosteriorWallOfSubdivisionOfStomach;
    part def <fma17472> InternalSurfaceOfPosteriorWallOfDuodenum :> InternalSurfaceOfSegmentOfDuodenum;
    part def <fma17440> InternalSurfaceOfPosteriorWallOfFundusOfStomach :> InternalSurfaceOfPosteriorWallOfSubdivisionOfStomach;
    part def <fma17442> InternalSurfaceOfPosteriorWallOfPyloricAntrum :> InternalSurfaceOfPosteriorWallOfSubdivisionOfStomach;
    part def <fma17443> InternalSurfaceOfPosteriorWallOfPyloricCanal :> InternalSurfaceOfPosteriorWallOfSubdivisionOfStomach;
    part def <fma17425> InternalSurfaceOfPosteriorWallOfStomach :> InternalSurfaceOfSubdivisionOfStomach;

    part def <fma15072> IntestinalVillus :> OrganComponentLayer {
        doc /* Organ component layer of intestine, each instance of which is a small, fingerlike projection into the lumen of some small intestine. */
    }

    part def <fma63300> IntestinalVillusOfDuodenum :> IntestinalVillus {
        part duodenalEpithelium : DuodenalEpithelium[1..*] :> regionalPartFeatures;
        part cryptOfLieberkuhnOfDuodenum : CryptOfLieberkuhnOfDuodenum[1..*] :> regionalPartFeatures;
        part laminaPropriaOfDuodenum : LaminaPropriaOfDuodenum[1..*] :> regionalPartFeatures;
    }

    part def <fma63301> IntestinalVillusOfJejunum :> IntestinalVillus {
        part jejunalEpithelium : JejunalEpithelium[1..*] :> regionalPartFeatures;
        part cryptOfLieberkuhnOfJejunum : CryptOfLieberkuhnOfJejunum[1..*] :> regionalPartFeatures;
        part laminaPropriaMucosaeOfJejunum : LaminaPropriaMucosaeOfJejunum[1..*] :> regionalPartFeatures;
    }
    part def <fma68412> IntramuralCapillaryPlexus :> CapillaryNetworkOfOrganComponent;
    part def <fma17232> JejunalEpithelium :> EpitheliumOfZoneOfSmallIntestine;

    part def <fma7207> Jejunum :> SegmentOfSmallIntestine {
        ref part continuousWithDuodenum : Duodenum[1..*] :> continuousWithFeatures;
        ref part continuousWithIleum : Ileum[1..*] :> continuousWithFeatures;
        part proximalPartOfJejunum : ProximalPartOfJejunum[1..*] :> regionalPartFeatures;
        part lumenOfJejunum : LumenOfJejunum[1..*] :> constitutionalPartFeatures;
        part wallOfJejunum : WallOfJejunum[1..*] :> constitutionalPartFeatures;
        part distalPartOfJejunum : DistalPartOfJejunum[1..*] :> regionalPartFeatures;
        part middlePartOfJejunum : MiddlePartOfJejunum[1..*] :> regionalPartFeatures;
        ref part lymphaticDrainageSuperiorMesentericLymphaticChain : SuperiorMesentericLymphaticChain[1..*] :> lymphaticDrainageFeatures;
        ref part developsFromMidgut : Midgut[1..*] :> developsFromFeatures;
    }
    part def <fma15970> LaminaPropriaMucosaeOfJejunum :> LaminaPropriaOfZoneOfSmallIntestine;
    part def <fma63051> LaminaPropriaOfAbdominalPartOfEsophagus :> LaminaPropria;
    part def <fma17501> LaminaPropriaOfBodyOfStomach :> LaminaPropria;
    part def <fma17499> LaminaPropriaOfCardiaOfStomach :> LaminaPropria;
    part def <fma63052> LaminaPropriaOfCervicalPartOfEsophagus :> LaminaPropria;
    part def <fma15972> LaminaPropriaOfDuodenum :> LaminaPropriaOfZoneOfSmallIntestine;

    part def <fma63050> LaminaPropriaOfEsophagus :> LaminaPropria {
        part denseRegularElasticTissueOfLaminaPropriaOfEsophagus : DenseRegularElasticTissueOfLaminaPropriaOfEsophagus[1..*] :> constitutionalPartFeatures;
        part organizedMucosaAssociatedLymphoidTissue : OrganizedMucosaAssociatedLymphoidTissue[1..*] :> constitutionalPartFeatures;
        part laminaPropriaOfCervicalPartOfEsophagus : LaminaPropriaOfCervicalPartOfEsophagus[1..*] :> regionalPartFeatures;
        part submucosalNervePlexus : SubmucosalNervePlexus[1..*] :> constitutionalPartFeatures;
        part diffuseMucosaAssociatedLymphoidTissue : DiffuseMucosaAssociatedLymphoidTissue[1..*] :> constitutionalPartFeatures;
        part laminaPropriaOfAbdominalPartOfEsophagus : LaminaPropriaOfAbdominalPartOfEsophagus[1..*] :> regionalPartFeatures;
        part laminaPropriaOfThoracicPartOfEsophagus : LaminaPropriaOfThoracicPartOfEsophagus[1..*] :> regionalPartFeatures;
    }
    part def <fma17500> LaminaPropriaOfFundusOfStomach :> LaminaPropria;
    part def <fma17502> LaminaPropriaOfPyloricAntrum :> LaminaPropria;
    part def <fma17503> LaminaPropriaOfPyloricCanal :> LaminaPropria;
    part def <fma17504> LaminaPropriaOfPylorus :> LaminaPropria;

    part def <fma17448> LaminaPropriaOfStomach :> LaminaPropria {
        part organizedMucosaAssociatedLymphoidTissue : OrganizedMucosaAssociatedLymphoidTissue[1..*] :> regionalPartFeatures;
        part intramuralCapillaryPlexus : IntramuralCapillaryPlexus[1..*] :> regionalPartFeatures;
        part diffuseMucosaAssociatedLymphoidTissue : DiffuseMucosaAssociatedLymphoidTissue[1..*] :> regionalPartFeatures;
        part areolarConnectiveTissueOfLaminaPropriaOfStomach : AreolarConnectiveTissueOfLaminaPropriaOfStomach[1..*] :> constitutionalPartFeatures;
    }
    part def <fma63053> LaminaPropriaOfThoracicPartOfEsophagus :> LaminaPropria;

    part def <fma63047> LongitudinalMuscleLayerOfAbdominalPartOfEsophagus :> LongitudinalMuscleLayerOfSegmentOfEsophagus {
        part intercellularMatrixOfLongitudinalMuscleLayerOfAbdominalPartOfEsophagus : IntercellularMatrixOfLongitudinalMuscleLayerOfAbdominalPartOfEsophagus[1..*] :> constitutionalPartFeatures;
    }
    part def <fma17288> LongitudinalMuscleLayerOfBodyOfStomach :> LongitudinalMuscleLayerOfZoneOfStomach;
    part def <fma17475> LongitudinalMuscleLayerOfCardiaOfStomach :> LongitudinalMuscleLayerOfZoneOfStomach;

    part def <fma63043> LongitudinalMuscleLayerOfCervicalPartOfEsophagus :> LongitudinalMuscleLayerOfSegmentOfEsophagus {
        part intercellularMatrixOfLongitudinalMuscleLayerOfCervicalPartOfEsophagus : IntercellularMatrixOfLongitudinalMuscleLayerOfCervicalPartOfEsophagus[1..*] :> constitutionalPartFeatures;
    }

    part def <fma14946> LongitudinalMuscleLayerOfDuodenum :> LongitudinalMuscleLayerOfZoneOfSmallIntestine {
        part areolarConnectiveTissueOfLongitudinalMuscleLayerOfDuodenum : AreolarConnectiveTissueOfLongitudinalMuscleLayerOfDuodenum[1..*] :> constitutionalPartFeatures;
        part smoothMuscleTissueOfLongitudinalMuscleLayerOfDuodenum : SmoothMuscleTissueOfLongitudinalMuscleLayerOfDuodenum[1..*] :> constitutionalPartFeatures;
    }
    part def <fma63573> LongitudinalMuscleLayerOfEsophagus :> OuterMuscleLayerOfOrgan;
    part def <fma17280> LongitudinalMuscleLayerOfFundusOfStomach :> LongitudinalMuscleLayerOfZoneOfStomach;
    part def <fma14953> LongitudinalMuscleLayerOfJejunum :> LongitudinalMuscleLayerOfZoneOfSmallIntestine;
    part def <fma17293> LongitudinalMuscleLayerOfPyloricAntrum :> LongitudinalMuscleLayerOfZoneOfStomach;
    part def <fma17298> LongitudinalMuscleLayerOfPyloricCanal :> LongitudinalMuscleLayerOfZoneOfStomach;
    part def <fma14910> LongitudinalMuscleLayerOfStomach :> OuterMuscleLayerOfOrgan;

    part def <fma63045> LongitudinalMuscleLayerOfThoracicPartOfEsophagus :> LongitudinalMuscleLayerOfSegmentOfEsophagus {
        part intercellularMatrixOfLongitudinalMuscleLayerOfThoracicPartOfEsophagus : IntercellularMatrixOfLongitudinalMuscleLayerOfThoracicPartOfEsophagus[1..*] :> constitutionalPartFeatures;
    }

    part def <fma14132> LumenOfAbdominalPartOfEsophagus :> LumenOfSegmentOfEsophagus {
        ref part continuousWithLumenOfCardiaOfStomach : LumenOfCardiaOfStomach[1..*] :> continuousWithFeatures;
        ref part continuousWithLumenOfThoracicPartOfEsophagus : LumenOfThoracicPartOfEsophagus[1..*] :> continuousWithFeatures;
    }
    part def <fma17186> LumenOfAscendingPartOfDuodenum :> LumenOfSegmentOfDuodenum;

    part def <fma17078> LumenOfBodyOfStomach :> LumenOfZoneOfStomach {
        ref part continuousWithLumenOfFundusOfStomach : LumenOfFundusOfStomach[1..*] :> continuousWithFeatures;
        part lumenOfFundusOfStomach : LumenOfFundusOfStomach[1..*] :> regionalPartFeatures;
        part lumenOfPyloricPartOfStomach : LumenOfPyloricPartOfStomach[1..*] :> regionalPartFeatures;
    }

    part def <fma259315> LumenOfCardiaOfStomach :> LumenOfZoneOfStomach {
        ref part continuousWithWallOfAbdominalPartOfEsophagus : WallOfAbdominalPartOfEsophagus[1..*] :> continuousWithFeatures;
        part lumenOfFundusOfStomach : LumenOfFundusOfStomach[1..*] :> regionalPartFeatures;
        ref part continuousWithLumenOfFundusOfStomach : LumenOfFundusOfStomach[1..*] :> continuousWithFeatures;
        ref part continuousWithLumenOfAbdominalPartOfEsophagus : LumenOfAbdominalPartOfEsophagus[1..*] :> continuousWithFeatures;
        part lumenOfAbdominalPartOfEsophagus : LumenOfAbdominalPartOfEsophagus[1..*] :> regionalPartFeatures;
    }

    part def <fma14130> LumenOfCervicalPartOfEsophagus :> LumenOfSegmentOfEsophagus {
        ref part continuousWithCavityOfPharynx : CavityOfPharynx[1..*] :> continuousWithFeatures;
        ref part continuousWithLumenOfThoracicPartOfEsophagus : LumenOfThoracicPartOfEsophagus[1..*] :> continuousWithFeatures;
    }
    part def <fma17184> LumenOfDescendingPartOfDuodenum :> LumenOfSegmentOfDuodenum;
    part def <fma17189> LumenOfDistalPartOfJejunum :> LumenOfZoneOfJejunum;
    part def <fma63232> LumenOfDuodenalGland :> LumenOfSmallIntestinalGland;

    part def <fma14589> LumenOfDuodenum :> OrganCavitySubdivision {
        ref part continuousWithPyloricOrifice : PyloricOrifice[1..*] :> continuousWithFeatures;
        ref part continuousWithLumenOfJejunum : LumenOfJejunum[1..*] :> continuousWithFeatures;
    }
    part def <fma63241> LumenOfEsophagealGland :> OrganCavitySubdivision;

    part def <fma9398> LumenOfEsophagus :> OrganCavity {
        ref part superiorToCavityOfStomach : CavityOfStomach[1..*] :> superiorToFeatures;
        ref part boundedByInternalSurfaceOfEsophagus : InternalSurfaceOfEsophagus[1..*] :> boundedByFeatures;
        ref part inferiorToCavityOfPharynx : CavityOfPharynx[1..*] :> inferiorToFeatures;
        ref part continuousWithCavityOfPharynx : CavityOfPharynx[1..*] :> continuousWithFeatures;
        ref part continuousWithCavityOfStomach : CavityOfStomach[1..*] :> continuousWithFeatures;
    }

    part def <fma17077> LumenOfFundusOfStomach :> LumenOfZoneOfStomach {
        ref part continuousWithLumenOfBodyOfStomach : LumenOfBodyOfStomach[1..*] :> continuousWithFeatures;
        ref part continuousWithLumenOfCardiaOfStomach : LumenOfCardiaOfStomach[1..*] :> continuousWithFeatures;
    }
    part def <fma17185> LumenOfHorizontalPartOfDuodenum :> LumenOfSegmentOfDuodenum;
    part def <fma14591> LumenOfIleum :> OrganCavitySubdivision;

    part def <fma14590> LumenOfJejunum :> OrganCavitySubdivision {
        ref part continuousWithLumenOfDuodenum : LumenOfDuodenum[1..*] :> continuousWithFeatures;
        ref part continuousWithLumenOfIleum : LumenOfIleum[1..*] :> continuousWithFeatures;
    }
    part def <fma17188> LumenOfMiddlePartOfJejunum :> LumenOfZoneOfJejunum;
    part def <fma17187> LumenOfProximalPartOfJejunum :> LumenOfZoneOfJejunum;

    part def <fma17079> LumenOfPyloricAntrum :> LumenOfZoneOfStomach {
        ref part continuousWithLumenOfPyloricCanal : LumenOfPyloricCanal[1..*] :> continuousWithFeatures;
    }

    part def <fma17080> LumenOfPyloricCanal :> LumenOfZoneOfStomach {
        ref part continuousWithLumenOfPyloricAntrum : LumenOfPyloricAntrum[1..*] :> continuousWithFeatures;
        ref part continuousWithPyloricOrifice : PyloricOrifice[1..*] :> continuousWithFeatures;
    }

    part def <fma322098> LumenOfPyloricPartOfStomach :> LumenOfZoneOfStomach {
        part lumenOfPyloricAntrum : LumenOfPyloricAntrum[1..*] :> regionalPartFeatures;
        part lumenOfPyloricCanal : LumenOfPyloricCanal[1..*] :> regionalPartFeatures;
        part pyloricOrifice : PyloricOrifice[1..*] :> regionalPartFeatures;
    }
    part def <fma14587> LumenOfSmallIntestine :> OrganCavitySubdivision;
    part def <fma17183> LumenOfSuperiorPartOfDuodenum :> LumenOfSegmentOfDuodenum;

    part def <fma14131> LumenOfThoracicPartOfEsophagus :> LumenOfSegmentOfEsophagus {
        ref part continuousWithLumenOfAbdominalPartOfEsophagus : LumenOfAbdominalPartOfEsophagus[1..*] :> continuousWithFeatures;
        ref part continuousWithLumenOfCervicalPartOfEsophagus : LumenOfCervicalPartOfEsophagus[1..*] :> continuousWithFeatures;
    }

    part def <fma15074> MajorDuodenalPapilla :> DuodenalPapilla {
        doc /* Duodenal papilla, each instance of which is site of opening of some conjoined bile duct and main pancreatic duct into lumen of some duodenum. */
        part hepatopancreaticAmpulla : HepatopancreaticAmpulla[1..*] :> regionalPartFeatures;
    }
    part def <fma263366> MesotheliumOfSerosaOfDuodenum :> MesotheliumOfRegionOfVisceralPeritoneum;
    part def <fma263368> MesotheliumOfSerosaOfJejunum :> MesotheliumOfRegionOfVisceralPeritoneum;
    part def <fma263410> MesotheliumOfSerosaOfStomach :> MesotheliumOfRegionOfVisceralPeritoneum;

    part def <fma16982> MiddlePartOfJejunum :> ZoneOfJejunum {
        part lumenOfMiddlePartOfJejunum : LumenOfMiddlePartOfJejunum[1..*] :> constitutionalPartFeatures;
        part wallOfMiddlePartOfJejunum : WallOfMiddlePartOfJejunum[1..*] :> constitutionalPartFeatures;
    }

    part def <fma15075> MinorDuodenalPapilla :> DuodenalPapilla {
        doc /* Duodenal papilla, each instance of which is site of opening of some accessory pancreatic duct into lumen of some duodenum. */
    }

    part def <fma63008> MucosaOfAbdominalPartOfEsophagus :> MucosaOfSegmentOfEsophagus {
        part laminaPropriaOfAbdominalPartOfEsophagus : LaminaPropriaOfAbdominalPartOfEsophagus[1..*] :> constitutionalPartFeatures;
        part epitheliumOfAbdominalPartOfEsophagus : EpitheliumOfAbdominalPartOfEsophagus[1..*] :> constitutionalPartFeatures;
        part muscularisMucosaeOfAbdominalPartOfEsophagus : MuscularisMucosaeOfAbdominalPartOfEsophagus[1..*] :> constitutionalPartFeatures;
    }
    part def <fma17104> MucosaOfAscendingPartOfDuodenum :> MucosaOfZoneOfDuodenum;

    part def <fma17054> MucosaOfBodyOfStomach :> MucosaOfZoneOfStomach {
        part muscularisMucosaeOfBodyOfStomach : MuscularisMucosaeOfBodyOfStomach[1..*] :> constitutionalPartFeatures;
        part laminaPropriaOfBodyOfStomach : LaminaPropriaOfBodyOfStomach[1..*] :> constitutionalPartFeatures;
        part principalGastricGland : PrincipalGastricGland[1..*] :> constitutionalPartFeatures;
        part epitheliumOfBodyOfStomach : EpitheliumOfBodyOfStomach[1..*] :> constitutionalPartFeatures;
        part principalGlandOfBodyOfStomach : PrincipalGlandOfBodyOfStomach[1..*] :> constitutionalPartFeatures;
    }

    part def <fma17456> MucosaOfCardiaOfStomach :> MucosaOfZoneOfStomach {
        part laminaPropriaOfCardiaOfStomach : LaminaPropriaOfCardiaOfStomach[1..*] :> constitutionalPartFeatures;
        part muscularisMucosaeOfCardiaOfStomach : MuscularisMucosaeOfCardiaOfStomach[1..*] :> constitutionalPartFeatures;
        part epitheliumOfCardiaOfStomach : EpitheliumOfCardiaOfStomach[1..*] :> constitutionalPartFeatures;
        part gastricCardiacGland : GastricCardiacGland[1..*] :> constitutionalPartFeatures;
    }

    part def <fma63009> MucosaOfCervicalPartOfEsophagus :> MucosaOfSegmentOfEsophagus {
        part laminaPropriaOfCervicalPartOfEsophagus : LaminaPropriaOfCervicalPartOfEsophagus[1..*] :> constitutionalPartFeatures;
        part epitheliumOfCervicalPartOfEsophagus : EpitheliumOfCervicalPartOfEsophagus[1..*] :> constitutionalPartFeatures;
        part muscularisMucosaeOfCervicalPartOfEsophagus : MuscularisMucosaeOfCervicalPartOfEsophagus[1..*] :> constitutionalPartFeatures;
    }
    part def <fma17102> MucosaOfDescendingPartOfDuodenum :> MucosaOfZoneOfDuodenum;
    part def <fma17132> MucosaOfDistalPartOfJejunum :> MucosaOfRegionOfJejunum;

    part def <fma14942> MucosaOfDuodenum :> MucosaOfZoneOfSmallIntestine {
        part intestinalVillusOfDuodenum : IntestinalVillusOfDuodenum[1..*] :> constitutionalPartFeatures;
        part muscularisMucosaeOfDuodenum : MuscularisMucosaeOfDuodenum[1..*] :> constitutionalPartFeatures;
    }

    part def <fma62996> MucosaOfEsophagus :> Mucosa {
        part cardiacEsophagealGland : CardiacEsophagealGland[1..*] :> regionalPartFeatures;
        part epitheliumOfEsophagus : EpitheliumOfEsophagus[1..*] :> constitutionalPartFeatures;
        part laminaPropriaOfEsophagus : LaminaPropriaOfEsophagus[1..*] :> constitutionalPartFeatures;
        part mucosaOfAbdominalPartOfEsophagus : MucosaOfAbdominalPartOfEsophagus[1..*] :> regionalPartFeatures;
        part muscularisMucosaeOfEsophagus : MuscularisMucosaeOfEsophagus[1..*] :> constitutionalPartFeatures;
        part mucosaOfCervicalPartOfEsophagus : MucosaOfCervicalPartOfEsophagus[1..*] :> regionalPartFeatures;
        part mucosaOfThoracicPartOfEsophagus : MucosaOfThoracicPartOfEsophagus[1..*] :> regionalPartFeatures;
    }

    part def <fma17053> MucosaOfFundusOfStomach :> MucosaOfZoneOfStomach {
        part principalGlandOfFundusOfStomach : PrincipalGlandOfFundusOfStomach[1..*] :> constitutionalPartFeatures;
        part laminaPropriaOfFundusOfStomach : LaminaPropriaOfFundusOfStomach[1..*] :> constitutionalPartFeatures;
        part principalGastricGland : PrincipalGastricGland[1..*] :> constitutionalPartFeatures;
        part epitheliumOfFundusOfStomach : EpitheliumOfFundusOfStomach[1..*] :> constitutionalPartFeatures;
        part muscularisMucosaeOfFundusOfStomach : MuscularisMucosaeOfFundusOfStomach[1..*] :> constitutionalPartFeatures;
    }
    part def <fma17103> MucosaOfHorizontalPartOfDuodenum :> MucosaOfZoneOfDuodenum;

    part def <fma14949> MucosaOfJejunum :> MucosaOfZoneOfSmallIntestine {
        part intestinalVillusOfJejunum : IntestinalVillusOfJejunum[1..*] :> constitutionalPartFeatures;
        part muscularisMucosaeOfJejunum : MuscularisMucosaeOfJejunum[1..*] :> constitutionalPartFeatures;
    }
    part def <fma17131> MucosaOfMiddlePartOfJejunum :> MucosaOfRegionOfJejunum;
    part def <fma17130> MucosaOfProximalPartOfJejunum :> MucosaOfRegionOfJejunum;

    part def <fma17055> MucosaOfPyloricAntrum :> MucosaOfZoneOfStomach {
        part epitheliumOfPyloricAntrum : EpitheliumOfPyloricAntrum[1..*] :> constitutionalPartFeatures;
        part laminaPropriaOfPyloricAntrum : LaminaPropriaOfPyloricAntrum[1..*] :> constitutionalPartFeatures;
        part muscularisMucosaeOfPyloricAntrum : MuscularisMucosaeOfPyloricAntrum[1..*] :> constitutionalPartFeatures;
        part pyloricGland : PyloricGland[1..*] :> constitutionalPartFeatures;
    }

    part def <fma17056> MucosaOfPyloricCanal :> MucosaOfZoneOfStomach {
        part epitheliumOfPyloricCanal : EpitheliumOfPyloricCanal[1..*] :> constitutionalPartFeatures;
        part laminaPropriaOfPyloricCanal : LaminaPropriaOfPyloricCanal[1..*] :> constitutionalPartFeatures;
        part muscularisMucosaeOfPyloricCanal : MuscularisMucosaeOfPyloricCanal[1..*] :> constitutionalPartFeatures;
        part pyloricGland : PyloricGland[1..*] :> constitutionalPartFeatures;
    }

    part def <fma17461> MucosaOfPylorus :> MucosaOfZoneOfStomach {
        part laminaPropriaOfPylorus : LaminaPropriaOfPylorus[1..*] :> constitutionalPartFeatures;
        part muscularisMucosaeOfPylorus : MuscularisMucosaeOfPylorus[1..*] :> constitutionalPartFeatures;
        part epitheliumOfPylorus : EpitheliumOfPylorus[1..*] :> constitutionalPartFeatures;
    }

    part def <fma14907> MucosaOfStomach :> Mucosa {
        part laminaPropriaOfStomach : LaminaPropriaOfStomach[1..*] :> constitutionalPartFeatures;
        part epitheliumOfStomach : EpitheliumOfStomach[1..*] :> constitutionalPartFeatures;
        part muscularisMucosaeOfStomach : MuscularisMucosaeOfStomach[1..*] :> constitutionalPartFeatures;
    }
    part def <fma17100> MucosaOfSuperiorPartOfDuodenum :> MucosaOfZoneOfDuodenum;

    part def <fma63010> MucosaOfThoracicPartOfEsophagus :> MucosaOfSegmentOfEsophagus {
        part muscularisMucosaeOfThoracicPartOfEsophagus : MuscularisMucosaeOfThoracicPartOfEsophagus[1..*] :> constitutionalPartFeatures;
        part epitheliumOfThoracicPartOfEsophagus : EpitheliumOfThoracicPartOfEsophagus[1..*] :> constitutionalPartFeatures;
        part laminaPropriaOfThoracicPartOfEsophagus : LaminaPropriaOfThoracicPartOfEsophagus[1..*] :> constitutionalPartFeatures;
    }
    part def <fma63042> MuscleLayerOfAbdominalPartOfEsophagus :> MuscleLayerOfSegmentOfEsophagus;
    part def <fma17116> MuscleLayerOfAscendingPartOfDuodenum :> MuscleLayerOfSubdivisionOfDuodenum;

    part def <fma17064> MuscleLayerOfBodyOfStomach :> MuscleLayerOfZoneOfStomach {
        part longitudinalMuscleLayerOfBodyOfStomach : LongitudinalMuscleLayerOfBodyOfStomach[1..*] :> regionalPartFeatures;
        part circularMuscleLayerOfBodyOfStomach : CircularMuscleLayerOfBodyOfStomach[1..*] :> regionalPartFeatures;
        part obliqueMuscleLayerOfBodyOfStomach : ObliqueMuscleLayerOfBodyOfStomach[1..*] :> regionalPartFeatures;
    }

    part def <fma17458> MuscleLayerOfCardiaOfStomach :> MuscleLayerOfZoneOfStomach {
        part longitudinalMuscleLayerOfCardiaOfStomach : LongitudinalMuscleLayerOfCardiaOfStomach[1..*] :> regionalPartFeatures;
        part obliqueMuscleLayerOfCardiaOfStomach : ObliqueMuscleLayerOfCardiaOfStomach[1..*] :> regionalPartFeatures;
        part circularMuscleLayerOfCardiaOfStomach : CircularMuscleLayerOfCardiaOfStomach[1..*] :> regionalPartFeatures;
    }
    part def <fma63040> MuscleLayerOfCervicalPartOfEsophagus :> MuscleLayerOfSegmentOfEsophagus;
    part def <fma17114> MuscleLayerOfDescendingPartOfDuodenum :> MuscleLayerOfSubdivisionOfDuodenum;
    part def <fma17140> MuscleLayerOfDistalPartOfJejunum :> MuscleLayerOfSubdivisionOfJejunum;

    part def <fma14944> MuscleLayerOfDuodenum :> MuscleLayerOfZoneOfSmallIntestine {
        part longitudinalMuscleLayerOfDuodenum : LongitudinalMuscleLayerOfDuodenum[1..*] :> regionalPartFeatures;
        part circularMuscleLayerOfDuodenum : CircularMuscleLayerOfDuodenum[1..*] :> regionalPartFeatures;
    }

    part def <fma62998> MuscleLayerOfEsophagus :> MuscleLayerOfDigestiveTract {
        part muscleLayerOfCervicalPartOfEsophagus : MuscleLayerOfCervicalPartOfEsophagus[1..*] :> regionalPartFeatures;
        part muscleLayerOfAbdominalPartOfEsophagus : MuscleLayerOfAbdominalPartOfEsophagus[1..*] :> regionalPartFeatures;
        part circularMuscleLayerOfEsophagus : CircularMuscleLayerOfEsophagus[1..*] :> constitutionalPartFeatures;
        part muscleLayerOfThoracicPartOfEsophagus : MuscleLayerOfThoracicPartOfEsophagus[1..*] :> regionalPartFeatures;
        part longitudinalMuscleLayerOfEsophagus : LongitudinalMuscleLayerOfEsophagus[1..*] :> constitutionalPartFeatures;
    }

    part def <fma17063> MuscleLayerOfFundusOfStomach :> MuscleLayerOfZoneOfStomach {
        part circularMuscleLayerOfFundusOfStomach : CircularMuscleLayerOfFundusOfStomach[1..*] :> regionalPartFeatures;
        part longitudinalMuscleLayerOfFundusOfStomach : LongitudinalMuscleLayerOfFundusOfStomach[1..*] :> regionalPartFeatures;
    }
    part def <fma17115> MuscleLayerOfHorizontalPartOfDuodenum :> MuscleLayerOfSubdivisionOfDuodenum;

    part def <fma14951> MuscleLayerOfJejunum :> MuscleLayerOfZoneOfSmallIntestine {
        part longitudinalMuscleLayerOfJejunum : LongitudinalMuscleLayerOfJejunum[1..*] :> regionalPartFeatures;
        part circularMuscleLayerOfJejunum : CircularMuscleLayerOfJejunum[1..*] :> regionalPartFeatures;
    }
    part def <fma17139> MuscleLayerOfMiddlePartOfJejunum :> MuscleLayerOfSubdivisionOfJejunum;
    part def <fma17138> MuscleLayerOfProximalPartOfJejunum :> MuscleLayerOfSubdivisionOfJejunum;

    part def <fma17065> MuscleLayerOfPyloricAntrum :> MuscleLayerOfZoneOfStomach {
        part longitudinalMuscleLayerOfPyloricAntrum : LongitudinalMuscleLayerOfPyloricAntrum[1..*] :> regionalPartFeatures;
        part circularMuscleLayerOfPyloricAntrum : CircularMuscleLayerOfPyloricAntrum[1..*] :> regionalPartFeatures;
    }

    part def <fma17066> MuscleLayerOfPyloricCanal :> MuscleLayerOfZoneOfStomach {
        part circularMuscleLayerOfPyloricCanal : CircularMuscleLayerOfPyloricCanal[1..*] :> regionalPartFeatures;
        part longitudinalMuscleLayerOfPyloricCanal : LongitudinalMuscleLayerOfPyloricCanal[1..*] :> regionalPartFeatures;
    }
    part def <fma17463> MuscleLayerOfPylorus :> MuscleLayerOfZoneOfStomach;

    part def <fma14909> MuscleLayerOfStomach :> MuscleLayerOfDigestiveTract {
        part obliqueMuscleLayerOfStomach : ObliqueMuscleLayerOfStomach[1..*] :> regionalPartFeatures;
        part longitudinalMuscleLayerOfStomach : LongitudinalMuscleLayerOfStomach[1..*] :> regionalPartFeatures;
        part circularMuscleLayerOfStomach : CircularMuscleLayerOfStomach[1..*] :> regionalPartFeatures;
    }
    part def <fma17112> MuscleLayerOfSuperiorPartOfDuodenum :> MuscleLayerOfSubdivisionOfDuodenum;
    part def <fma63041> MuscleLayerOfThoracicPartOfEsophagus :> MuscleLayerOfSegmentOfEsophagus;
    part def <fma63062> MuscularisMucosaeOfAbdominalPartOfEsophagus :> MuscularisMucosaeOfSegmentOfEsophagus;
    part def <fma17286> MuscularisMucosaeOfBodyOfStomach :> MuscularisMucosaeOfZoneOfStomach;
    part def <fma17470> MuscularisMucosaeOfCardiaOfStomach :> MuscularisMucosaeOfZoneOfStomach;
    part def <fma63058> MuscularisMucosaeOfCervicalPartOfEsophagus :> MuscularisMucosaeOfSegmentOfEsophagus;

    part def <fma15059> MuscularisMucosaeOfDuodenum :> MuscularisMucosae {
        part intercellularMatrixOfMuscularisMucosaeOfDuodenum : IntercellularMatrixOfMuscularisMucosaeOfDuodenum[1..*] :> constitutionalPartFeatures;
    }

    part def <fma63059> MuscularisMucosaeOfEsophagus :> MuscularisMucosae {
        part muscularisMucosaeOfAbdominalPartOfEsophagus : MuscularisMucosaeOfAbdominalPartOfEsophagus[1..*] :> regionalPartFeatures;
        part muscularisMucosaeOfThoracicPartOfEsophagus : MuscularisMucosaeOfThoracicPartOfEsophagus[1..*] :> regionalPartFeatures;
        part muscularisMucosaeOfCervicalPartOfEsophagus : MuscularisMucosaeOfCervicalPartOfEsophagus[1..*] :> regionalPartFeatures;
    }
    part def <fma17278> MuscularisMucosaeOfFundusOfStomach :> MuscularisMucosaeOfZoneOfStomach;
    part def <fma15063> MuscularisMucosaeOfJejunum :> MuscularisMucosaeOfZoneOfSmallIntestine;
    part def <fma17292> MuscularisMucosaeOfPyloricAntrum :> MuscularisMucosaeOfZoneOfStomach;
    part def <fma17297> MuscularisMucosaeOfPyloricCanal :> MuscularisMucosaeOfZoneOfStomach;
    part def <fma17473> MuscularisMucosaeOfPylorus :> MuscularisMucosaeOfZoneOfStomach;

    part def <fma14924> MuscularisMucosaeOfStomach :> MuscularisMucosae {
        part outerLongitudinalLayerOfMuscularisMucosaeOfStomach : OuterLongitudinalLayerOfMuscularisMucosaeOfStomach[1..*] :> constitutionalPartFeatures;
        part muscularisMucosaeOfFundusOfStomach : MuscularisMucosaeOfFundusOfStomach[1..*] :> regionalPartFeatures;
        part muscularisMucosaeOfCardiaOfStomach : MuscularisMucosaeOfCardiaOfStomach[1..*] :> regionalPartFeatures;
        part muscularisMucosaeOfBodyOfStomach : MuscularisMucosaeOfBodyOfStomach[1..*] :> regionalPartFeatures;
        part muscularisMucosaeOfPylorus : MuscularisMucosaeOfPylorus[1..*] :> regionalPartFeatures;
        part muscularisMucosaeOfPyloricCanal : MuscularisMucosaeOfPyloricCanal[1..*] :> regionalPartFeatures;
        part innerCircularLayerOfMuscularisMucosaeOfStomach : InnerCircularLayerOfMuscularisMucosaeOfStomach[1..*] :> constitutionalPartFeatures;
        part muscularisMucosaeOfPyloricAntrum : MuscularisMucosaeOfPyloricAntrum[1..*] :> regionalPartFeatures;
    }
    part def <fma63061> MuscularisMucosaeOfThoracicPartOfEsophagus :> MuscularisMucosaeOfSegmentOfEsophagus;
    part def <fma17290> ObliqueMuscleLayerOfBodyOfStomach :> MiddleMuscleLayerOfZoneOfStomach;
    part def <fma17482> ObliqueMuscleLayerOfCardiaOfStomach :> MiddleMuscleLayerOfZoneOfStomach;
    part def <fma14912> ObliqueMuscleLayerOfStomach :> MiddleMuscleLayerOfOrgan;
    part def <fma62836> OrganizedMucosaAssociatedLymphoidTissue :> MucosaAssociatedLymphoidTissue;
    part def <fma54879> Oropharynx :> SubdivisionOfPharynx;
    part def <fma63530> OuterLongitudinalLayerOfMuscularisMucosaeOfStomach :> MuscularisMucosae;

    part def <fma0326748> PosteriorMediastinalSegmentOfEsophagus :> SegmentOfEsophagus {
        part t7SegmentOfEsophagus : T7SegmentOfEsophagus[1..*] :> regionalPartFeatures;
        part t5SegmentOfEsophagus : T5SegmentOfEsophagus[1..*] :> regionalPartFeatures;
        part t6SegmentOfEsophagus : T6SegmentOfEsophagus[1..*] :> regionalPartFeatures;
        part t9SegmentOfEsophagus : T9SegmentOfEsophagus[1..*] :> regionalPartFeatures;
        part t10SegmentOfEsophagus : T10SegmentOfEsophagus[1..*] :> regionalPartFeatures;
        part t8SegmentOfEsophagus : T8SegmentOfEsophagus[1..*] :> regionalPartFeatures;
    }
    part def <fma17418> PosteriorWallOfAscendingPartOfDuodenum :> RegionOfWallOfDuodenum_fma86109;

    part def <fma17403> PosteriorWallOfBodyOfStomach :> PosteriorWallOfZoneOfStomach {
        part internalSurfaceOfPosteriorWallOfBodyOfStomach : InternalSurfaceOfPosteriorWallOfBodyOfStomach[1..*] :> regionalPartFeatures;
    }
    part def <fma17435> PosteriorWallOfCardiaOfStomach :> PosteriorWallOfZoneOfStomach;
    part def <fma17416> PosteriorWallOfDescendingPartOfDuodenum :> RegionOfWallOfDuodenum_fma86109;
    part def <fma86665> PosteriorWallOfDistalPartOfJejunum :> RegionOfWallOfJejunum;

    part def <fma17408> PosteriorWallOfDuodenum :> RegionOfWallOfDuodenum_fma86109 {
        part submucosaOfPosteriorWallOfDuodenum : SubmucosaOfPosteriorWallOfDuodenum[1..*] :> constitutionalPartFeatures;
        part internalSurfaceOfPosteriorWallOfDuodenum : InternalSurfaceOfPosteriorWallOfDuodenum[1..*] :> regionalPartFeatures;
    }

    part def <fma17402> PosteriorWallOfFundusOfStomach :> PosteriorWallOfZoneOfStomach {
        part internalSurfaceOfPosteriorWallOfFundusOfStomach : InternalSurfaceOfPosteriorWallOfFundusOfStomach[1..*] :> regionalPartFeatures;
    }
    part def <fma17417> PosteriorWallOfHorizontalPartOfDuodenum :> RegionOfWallOfDuodenum_fma86109;
    part def <fma86663> PosteriorWallOfMiddlePartOfJejunum :> RegionOfWallOfJejunum;
    part def <fma86661> PosteriorWallOfProximalPartOfJejunum :> RegionOfWallOfJejunum;

    part def <fma17404> PosteriorWallOfPyloricAntrum :> PosteriorWallOfZoneOfStomach {
        part internalSurfaceOfPosteriorWallOfPyloricAntrum : InternalSurfaceOfPosteriorWallOfPyloricAntrum[1..*] :> regionalPartFeatures;
    }

    part def <fma17405> PosteriorWallOfPyloricCanal :> PosteriorWallOfZoneOfStomach {
        part internalSurfaceOfPosteriorWallOfPyloricCanal : InternalSurfaceOfPosteriorWallOfPyloricCanal[1..*] :> regionalPartFeatures;
    }
    part def <fma17439> PosteriorWallOfPylorus :> PosteriorWallOfZoneOfStomach;

    part def <fma14584> PosteriorWallOfStomach :> RegionOfWallOfStomach {
        part internalSurfaceOfPosteriorWallOfStomach : InternalSurfaceOfPosteriorWallOfStomach[1..*] :> regionalPartFeatures;
    }
    part def <fma17415> PosteriorWallOfSuperiorPartOfDuodenum :> RegionOfWallOfDuodenum_fma86109;
    part def <fma0326832> Prepylorus :> ZoneOfStomach;
    part def <fma14921> PrincipalGastricGland :> GastricGland;
    part def <fma17087> PrincipalGlandOfBodyOfStomach :> PrincipalGastricGland;
    part def <fma14923> PrincipalGlandOfFundusOfStomach :> PrincipalGastricGland;

    part def <fma71133> ProximalHalfOfDuodenum :> ZoneOfDuodenum {
        ref part developsFromForegut : Foregut[1..*] :> developsFromFeatures;
    }

    part def <fma16981> ProximalPartOfJejunum :> ZoneOfJejunum {
        part lumenOfProximalPartOfJejunum : LumenOfProximalPartOfJejunum[1..*] :> constitutionalPartFeatures;
        part wallOfProximalPartOfJejunum : WallOfProximalPartOfJejunum[1..*] :> constitutionalPartFeatures;
    }

    part def <fma14579> PyloricAntrum :> ZoneOfStomach {
        part wallOfPyloricAntrum : WallOfPyloricAntrum[1..*] :> constitutionalPartFeatures;
        ref part lymphaticDrainageGastricLymphaticChain : GastricLymphaticChain[1..*] :> lymphaticDrainageFeatures;
        ref part lymphaticDrainagePyloricLymphaticChain : PyloricLymphaticChain[1..*] :> lymphaticDrainageFeatures;
        part lumenOfPyloricAntrum : LumenOfPyloricAntrum[1..*] :> constitutionalPartFeatures;
    }

    part def <fma14580> PyloricCanal :> ZoneOfStomach {
        ref part lymphaticDrainagePyloricLymphaticChain : PyloricLymphaticChain[1..*] :> lymphaticDrainageFeatures;
        ref part lymphaticDrainageGastricLymphaticChain : GastricLymphaticChain[1..*] :> lymphaticDrainageFeatures;
        part wallOfPyloricCanal : WallOfPyloricCanal[1..*] :> constitutionalPartFeatures;
        part lumenOfPyloricCanal : LumenOfPyloricCanal[1..*] :> constitutionalPartFeatures;
    }
    part def <fma14922> PyloricGland :> GastricGland;

    part def <fma14565> PyloricOrifice :> OrificeOfStomach {
        ref part continuousWithLumenOfDuodenum : LumenOfDuodenum[1..*] :> continuousWithFeatures;
        ref part continuousWithLumenOfPyloricCanal : LumenOfPyloricCanal[1..*] :> continuousWithFeatures;
    }

    part def <fma14581> Pylorus :> ZoneOfStomach {
        part wallOfPylorus : WallOfPylorus[1..*] :> constitutionalPartFeatures;
        ref part lymphaticDrainagePyloricLymphaticChain : PyloricLymphaticChain[1..*] :> lymphaticDrainageFeatures;
        part pyloricOrifice : PyloricOrifice[1..*] :> constitutionalPartFeatures;
        ref part lymphaticDrainageInferiorPartOfLeftGastricLymphaticChain : InferiorPartOfLeftGastricLymphaticChain[1..*] :> lymphaticDrainageFeatures;
    }
    part def <fma17128> SerosaOfAscendingPartOfDuodenum :> SerosaOfZoneOfDuodenum;
    part def <fma17074> SerosaOfBodyOfStomach :> SerosaOfZoneOfStomach;
    part def <fma17460> SerosaOfCardiaOfStomach :> SerosaOfZoneOfStomach;
    part def <fma17126> SerosaOfDescendingPartOfDuodenum :> SerosaOfZoneOfDuodenum;
    part def <fma17148> SerosaOfDistalPartOfJejunum :> SerosaOfZoneOfJejunum;

    part def <fma14948> SerosaOfDuodenum :> SerosaOfZoneOfSmallIntestine {
        part serosaOfHorizontalPartOfDuodenum : SerosaOfHorizontalPartOfDuodenum[1..*] :> regionalPartFeatures;
        part serosaOfDescendingPartOfDuodenum : SerosaOfDescendingPartOfDuodenum[1..*] :> regionalPartFeatures;
        part serosaOfSuperiorPartOfDuodenum : SerosaOfSuperiorPartOfDuodenum[1..*] :> regionalPartFeatures;
        part connectiveTissueOfSerosaOfDuodenum : ConnectiveTissueOfSerosaOfDuodenum[1..*] :> constitutionalPartFeatures;
        part mesotheliumOfSerosaOfDuodenum : MesotheliumOfSerosaOfDuodenum[1..*] :> constitutionalPartFeatures;
        part serosaOfAscendingPartOfDuodenum : SerosaOfAscendingPartOfDuodenum[1..*] :> regionalPartFeatures;
    }
    part def <fma63057> SerosaOfEsophagus :> SerosaOfOrgan;
    part def <fma17073> SerosaOfFundusOfStomach :> SerosaOfZoneOfStomach;
    part def <fma17127> SerosaOfHorizontalPartOfDuodenum :> SerosaOfZoneOfDuodenum;

    part def <fma14955> SerosaOfJejunum :> SerosaOfZoneOfSmallIntestine {
        part mesotheliumOfSerosaOfJejunum : MesotheliumOfSerosaOfJejunum[1..*] :> constitutionalPartFeatures;
    }
    part def <fma17147> SerosaOfMiddlePartOfJejunum :> SerosaOfZoneOfJejunum;
    part def <fma17146> SerosaOfProximalPartOfJejunum :> SerosaOfZoneOfJejunum;
    part def <fma17075> SerosaOfPyloricAntrum :> SerosaOfZoneOfStomach;
    part def <fma17076> SerosaOfPyloricCanal :> SerosaOfZoneOfStomach;
    part def <fma17465> SerosaOfPylorus :> SerosaOfZoneOfStomach;

    part def <fma14914> SerosaOfStomach :> SerosaOfOrgan {
        part serosaOfFundusOfStomach : SerosaOfFundusOfStomach[1..*] :> regionalPartFeatures;
        part serosaOfCardiaOfStomach : SerosaOfCardiaOfStomach[1..*] :> regionalPartFeatures;
        part serosaOfPyloricAntrum : SerosaOfPyloricAntrum[1..*] :> regionalPartFeatures;
        part mesotheliumOfSerosaOfStomach : MesotheliumOfSerosaOfStomach[1..*] :> constitutionalPartFeatures;
        part connectiveTissueOfSerosaOfStomach : ConnectiveTissueOfSerosaOfStomach[1..*] :> constitutionalPartFeatures;
        part serosaOfPyloricCanal : SerosaOfPyloricCanal[1..*] :> regionalPartFeatures;
        part serosaOfBodyOfStomach : SerosaOfBodyOfStomach[1..*] :> regionalPartFeatures;
        part serosaOfPylorus : SerosaOfPylorus[1..*] :> regionalPartFeatures;
    }
    part def <fma17124> SerosaOfSuperiorPartOfDuodenum :> SerosaOfZoneOfDuodenum;

    part def <fma7200> SmallIntestine :> OrganWithOrganCavity {
        doc /* Organ with organ cavity, each instance of which is proximally continuous_with some stomach; distally continuous_with some large intestine. Examples: There is only one stomach. */
    }
    part def <fma262014> SmoothMuscleTissueOfCircularMuscleLayerOfDuodenum :> SmoothMuscleTissue;
    part def <fma262016> SmoothMuscleTissueOfLongitudinalMuscleLayerOfDuodenum :> SmoothMuscleTissue;

    part def <fma7148> Stomach :> OrganWithOrganCavity {
        doc /* Organ with organ cavity, each instance of which is proximally continuous_with some esophagus; distally continuous_with some duodenum. Examples: There is only one stomach. */
        ref part arterialSupplyShortGastricArtery : ShortGastricArtery[1..*] :> arterialSupplyFeatures;
        ref part nerveSupplyCeliacNervePlexus : CeliacNervePlexus[1..*] :> nerveSupplyFeatures;
        ref part boundedBySurfaceOfStomach : SurfaceOfStomach[1..*] :> boundedByFeatures;
        ref part nerveSupplyLeftPhrenicNervePlexus : LeftPhrenicNervePlexus[1..*] :> nerveSupplyFeatures;
        ref part venousDrainageRightGastroepiploicVein : RightGastroepiploicVein[1..*] :> venousDrainageFeatures;
        ref part continuousWithSmallIntestine : SmallIntestine[1..*] :> continuousWithFeatures;
        ref part distalToEsophagus : Esophagus[1..*] :> distalToFeatures;
        ref part directLeftOfAbdominalAorta : AbdominalAorta[1..*] :> directLeftOfFeatures;
        ref part lymphaticDrainagePancreaticLymphaticChain : PancreaticLymphaticChain[1..*] :> lymphaticDrainageFeatures;
        ref part venousDrainageLeftGastricVein : LeftGastricVein[1..*] :> venousDrainageFeatures;
        ref part nerveSupplyGastricBranchOfRightVagusNerve : GastricBranchOfRightVagusNerve[1..*] :> nerveSupplyFeatures;
        part bodyOfStomach : BodyOfStomach[1..*] :> regionalPartFeatures;
        ref part proximalToSmallIntestine : SmallIntestine[1..*] :> proximalToFeatures;
        ref part posteriorToGreaterOmentum : GreaterOmentum[1..*] :> posteriorToFeatures;
        part pyloricAntrum : PyloricAntrum[1..*] :> regionalPartFeatures;
        ref part developsFromForegut : Foregut[1..*] :> developsFromFeatures;
        ref part containedInAbdominalCavity : AbdominalCavity[1..*] :> containedInFeatures;
        ref part anteriorToSpleen : Spleen[1..*] :> anteriorToFeatures;
        ref part nerveSupplyHepaticNervePlexus : HepaticNervePlexus[1..*] :> nerveSupplyFeatures;
        part cavityOfStomach : CavityOfStomach[1..*] :> constitutionalPartFeatures;
        ref part directRightOfSpleen : Spleen[1..*] :> directRightOfFeatures;
        ref part inferiorToDiaphragm : Diaphragm[1..*] :> inferiorToFeatures;
        part pylorus : Pylorus[1..*] :> regionalPartFeatures;
        ref part venousDrainageShortGastricVein : ShortGastricVein[1..*] :> venousDrainageFeatures;
        ref part anteriorToAbdominalAorta : AbdominalAorta[1..*] :> anteriorToFeatures;
        ref part nerveSupplyGastricBranchOfLeftVagusNerve : GastricBranchOfLeftVagusNerve[1..*] :> nerveSupplyFeatures;
        ref part continuousDistallyWithSmallIntestine : SmallIntestine[1..*] :> continuousDistallyWithFeatures;
        ref part nerveSupplyLeftGastricNervePlexus : LeftGastricNervePlexus[1..*] :> nerveSupplyFeatures;
        part gastroduodenalJunction : GastroduodenalJunction[1..*] :> regionalPartFeatures;
        ref part directRightOfDiaphragm : Diaphragm[1..*] :> directRightOfFeatures;
        part cardiaOfStomach : CardiaOfStomach[1..*] :> regionalPartFeatures;
        ref part arterialSupplyGastricBranchOfRightGastroEpiploicArtery : GastricBranchOfRightGastroEpiploicArtery[1..*] :> arterialSupplyFeatures;
        ref part continuousWithEsophagus : Esophagus[1..*] :> continuousWithFeatures;
        part wallOfStomach : WallOfStomach[1..*] :> constitutionalPartFeatures;
        ref part superiorToTransverseColon : TransverseColon[1..*] :> superiorToFeatures;
        part fundusOfStomach : FundusOfStomach[1..*] :> regionalPartFeatures;
        ref part venousDrainageLeftGastroepiploicVein : LeftGastroepiploicVein[1..*] :> venousDrainageFeatures;
        part pyloricCanal : PyloricCanal[1..*] :> regionalPartFeatures;
        ref part arterialSupplyGastricBranchOfLeftGastroEpiploicArtery : GastricBranchOfLeftGastroEpiploicArtery[1..*] :> arterialSupplyFeatures;
        ref part venousDrainageRightGastricVein : RightGastricVein[1..*] :> venousDrainageFeatures;
        ref part arterialSupplyRightGastricArtery : RightGastricArtery[1..*] :> arterialSupplyFeatures;
        ref part arterialSupplyLeftGastricArtery : LeftGastricArtery[1..*] :> arterialSupplyFeatures;
        ref part lymphaticDrainageHepaticLymphaticChain : HepaticLymphaticChain[1..*] :> lymphaticDrainageFeatures;
        ref part arterialSupplyPosteriorGastricArtery : PosteriorGastricArtery[1..*] :> arterialSupplyFeatures;
    }
    part def <fma67650> StratumCorneumOfEsophagealEpithelium :> LayerOfEpitheliumOfEsophagus;
    part def <fma67645> StratumGerminativumOfEsophagealEpithelium :> LayerOfEpitheliumOfEsophagus;
    part def <fma67647> StratumSpinosumOfEsophagealEpithelium :> LayerOfEpitheliumOfEsophagus;
    part def <fma67603> SubmucosalGlandOfEsophagus :> EsophagealGland;
    part def <fma21542> SubmucosalNervePlexus :> IntramuralNervePlexus;
    part def <fma63038> SubmucosaOfAbdominalPartOfEsophagus :> SubmucosaOfSegmentOfEsophagus;
    part def <fma20162> SubmucosaOfAnteriorWallOfDuodenum :> SubmucosaOfZoneOfDuodenum;
    part def <fma17110> SubmucosaOfAscendingPartOfDuodenum :> SubmucosaOfZoneOfDuodenum;
    part def <fma17059> SubmucosaOfBodyOfStomach :> SubmucosaOfZoneOfStomach;
    part def <fma17457> SubmucosaOfCardiaOfStomach :> SubmucosaOfZoneOfStomach;
    part def <fma63036> SubmucosaOfCervicalPartOfEsophagus :> SubmucosaOfSegmentOfEsophagus;
    part def <fma17108> SubmucosaOfDescendingPartOfDuodenum :> SubmucosaOfZoneOfDuodenum;
    part def <fma17136> SubmucosaOfDistalPartOfJejunum :> SubmucosaOfRegionOfJejunum;

    part def <fma14943> SubmucosaOfDuodenum :> SubmucosaOfZoneOfSmallIntestine {
        part areolarConnectiveTissueOfSubmucosaOfDuodenum : AreolarConnectiveTissueOfSubmucosaOfDuodenum[1..*] :> constitutionalPartFeatures;
        part duodenalGland : DuodenalGland[1..*] :> regionalPartFeatures;
    }

    part def <fma62997> SubmucosaOfEsophagus :> Submucosa {
        part denseRegularCollagenousTissueOfSubmucosaOfEsophagus : DenseRegularCollagenousTissueOfSubmucosaOfEsophagus[1..*] :> constitutionalPartFeatures;
        part submucosaOfThoracicPartOfEsophagus : SubmucosaOfThoracicPartOfEsophagus[1..*] :> regionalPartFeatures;
        part submucosaOfCervicalPartOfEsophagus : SubmucosaOfCervicalPartOfEsophagus[1..*] :> regionalPartFeatures;
        part submucosalGlandOfEsophagus : SubmucosalGlandOfEsophagus[1..*] :> constitutionalPartFeatures;
        part submucosaOfAbdominalPartOfEsophagus : SubmucosaOfAbdominalPartOfEsophagus[1..*] :> regionalPartFeatures;
    }
    part def <fma17058> SubmucosaOfFundusOfStomach :> SubmucosaOfZoneOfStomach;
    part def <fma17109> SubmucosaOfHorizontalPartOfDuodenum :> SubmucosaOfZoneOfDuodenum;
    part def <fma14950> SubmucosaOfJejunum :> SubmucosaOfZoneOfSmallIntestine;
    part def <fma17135> SubmucosaOfMiddlePartOfJejunum :> SubmucosaOfRegionOfJejunum;
    part def <fma20163> SubmucosaOfPosteriorWallOfDuodenum :> SubmucosaOfZoneOfDuodenum;
    part def <fma17134> SubmucosaOfProximalPartOfJejunum :> SubmucosaOfRegionOfJejunum;
    part def <fma17060> SubmucosaOfPyloricAntrum :> SubmucosaOfZoneOfStomach;
    part def <fma17061> SubmucosaOfPyloricCanal :> SubmucosaOfZoneOfStomach;
    part def <fma17462> SubmucosaOfPylorus :> SubmucosaOfZoneOfStomach;
    part def <fma14908> SubmucosaOfStomach :> Submucosa;
    part def <fma17106> SubmucosaOfSuperiorPartOfDuodenum :> SubmucosaOfZoneOfDuodenum;
    part def <fma63037> SubmucosaOfThoracicPartOfEsophagus :> SubmucosaOfSegmentOfEsophagus;
    part def <fma17122> SubserosaOfAscendingPartOfDuodenum :> SubserosaOfZoneOfDuodenum;
    part def <fma17069> SubserosaOfBodyOfStomach :> SubserosaOfZoneOfStomach;
    part def <fma17459> SubserosaOfCardiaOfStomach :> SubserosaOfZoneOfStomach;
    part def <fma17120> SubserosaOfDescendingPartOfDuodenum :> SubserosaOfZoneOfDuodenum;
    part def <fma17144> SubserosaOfDistalPartOfJejunum :> SubserosaOfZoneOfJejunum;
    part def <fma14947> SubserosaOfDuodenum :> SubserosaOfZoneOfSmallIntestine;
    part def <fma17068> SubserosaOfFundusOfStomach :> SubserosaOfZoneOfStomach;
    part def <fma17121> SubserosaOfHorizontalPartOfDuodenum :> SubserosaOfZoneOfDuodenum;
    part def <fma14954> SubserosaOfJejunum :> SubserosaOfZoneOfSmallIntestine;
    part def <fma17143> SubserosaOfMiddlePartOfJejunum :> SubserosaOfZoneOfJejunum;
    part def <fma17142> SubserosaOfProximalPartOfJejunum :> SubserosaOfZoneOfJejunum;
    part def <fma17070> SubserosaOfPyloricAntrum :> SubserosaOfZoneOfStomach;
    part def <fma17071> SubserosaOfPyloricCanal :> SubserosaOfZoneOfStomach;
    part def <fma17464> SubserosaOfPylorus :> SubserosaOfZoneOfStomach;
    part def <fma14913> SubserosaOfStomach :> SubserosaOfOrgan;
    part def <fma17118> SubserosaOfSuperiorPartOfDuodenum :> SubserosaOfZoneOfDuodenum;
    part def <fma15955> SuperiorFlexureOfDuodenum :> FlexureOfDuodenum;

    part def <fma0326749> SuperiorMediastinalSegmentOfEsophagus :> SegmentOfEsophagus {
        part t3SegmentOfEsophagus : T3SegmentOfEsophagus[1..*] :> regionalPartFeatures;
        part t4SegmentOfEsophagus : T4SegmentOfEsophagus[1..*] :> regionalPartFeatures;
        part t1SegmentOfEsophagus : T1SegmentOfEsophagus[1..*] :> regionalPartFeatures;
        part t2SegmentOfEsophagus : T2SegmentOfEsophagus[1..*] :> regionalPartFeatures;
    }

    part def <fma14926> SuperiorPartOfDuodenum :> SegmentOfDuodenum {
        part lumenOfSuperiorPartOfDuodenum : LumenOfSuperiorPartOfDuodenum[1..*] :> constitutionalPartFeatures;
        part wallOfSuperiorPartOfDuodenum : WallOfSuperiorPartOfDuodenum[1..*] :> constitutionalPartFeatures;
        part superiorPartProperOfDuodenum : SuperiorPartProperOfDuodenum[1..*] :> regionalPartFeatures;
        part duodenalBulb : DuodenalBulb[1..*] :> regionalPartFeatures;
        ref part lymphaticDrainageGastricLymphaticChain : GastricLymphaticChain[1..*] :> lymphaticDrainageFeatures;
        ref part lymphaticDrainagePyloricLymphaticChain : PyloricLymphaticChain[1..*] :> lymphaticDrainageFeatures;
    }
    part def <fma265215> SuperiorPartProperOfDuodenum :> SegmentOfDuodenum;
    part def <fma280987> SystemicCapillaryNetworkOfCardinalOrganPart :> SystemicCapillaryPlexus;
    part def <fma264934> SystemicCapillaryPlexus :> CapillaryPlexus;

    part def <fma52537> T10SegmentOfEsophagus :> VertebralSegmentOfEsophagus {
        ref part posteriorToRightCrusOfLumbarPartOfDiaphragm : RightCrusOfLumbarPartOfDiaphragm[1..*] :> posteriorToFeatures;
        part t10SegmentProperOfEsophagus : T10SegmentProperOfEsophagus[1..*] :> regionalPartFeatures;
        ref part anteriorToLeftCrusOfLumbarPartOfDiaphragm : LeftCrusOfLumbarPartOfDiaphragm[1..*] :> anteriorToFeatures;
        ref part directLeftOfRightCrusOfLumbarPartOfDiaphragm : RightCrusOfLumbarPartOfDiaphragm[1..*] :> directLeftOfFeatures;
        ref part medialToRightCrusOfLumbarPartOfDiaphragm : RightCrusOfLumbarPartOfDiaphragm[1..*] :> medialToFeatures;
        part esophagealSegmentOfEsophagogastricJunction : EsophagealSegmentOfEsophagogastricJunction[1..*] :> regionalPartFeatures;
        ref part directRightOfLeftCrusOfLumbarPartOfDiaphragm : LeftCrusOfLumbarPartOfDiaphragm[1..*] :> directRightOfFeatures;
        ref part directRightOfRightCrusOfLumbarPartOfDiaphragm : RightCrusOfLumbarPartOfDiaphragm[1..*] :> directRightOfFeatures;
        ref part anteriorToT10PartOfThoracicAorta : T10PartOfThoracicAorta[1..*] :> anteriorToFeatures;
        ref part directRightOfT10PartOfThoracicAorta : T10PartOfThoracicAorta[1..*] :> directRightOfFeatures;
        ref part medialToLeftCrusOfLumbarPartOfDiaphragm : LeftCrusOfLumbarPartOfDiaphragm[1..*] :> medialToFeatures;
    }
    part def <fma255862> T10SegmentProperOfEsophagus :> SubdivisionOfVertebralSegmentOfEsophagus;

    part def <fma52529> T1SegmentOfEsophagus :> VertebralSegmentOfEsophagus {
        ref part directLeftOfBodyOfFirstThoracicVertebra : BodyOfFirstThoracicVertebra[1..*] :> directLeftOfFeatures;
        ref part containedInSuperiorMediastinalSpace : SuperiorMediastinalSpace[1..*] :> containedInFeatures;
        ref part directRightOfT1PartOfLeftLongusColli : T1PartOfLeftLongusColli[1..*] :> directRightOfFeatures;
        ref part directLeftOfEndothoracicFascia : EndothoracicFascia[1..*] :> directLeftOfFeatures;
        ref part anteriorToT1PartOfLeftLongusColli : T1PartOfLeftLongusColli[1..*] :> anteriorToFeatures;
        ref part directLeftOfT1PartOfRightLongusColli : T1PartOfRightLongusColli[1..*] :> directLeftOfFeatures;
        ref part directLeftOfT1SegmentOfTrachea : T1SegmentOfTrachea[1..*] :> directLeftOfFeatures;
        ref part anteriorToBodyOfFirstThoracicVertebra : BodyOfFirstThoracicVertebra[1..*] :> anteriorToFeatures;
        ref part directRightOfT1SegmentOfTrachea : T1SegmentOfTrachea[1..*] :> directRightOfFeatures;
        ref part posteriorToT1SegmentOfTrachea : T1SegmentOfTrachea[1..*] :> posteriorToFeatures;
        ref part anteriorToT1PartOfRightLongusColli : T1PartOfRightLongusColli[1..*] :> anteriorToFeatures;
        ref part directRightOfBodyOfFirstThoracicVertebra : BodyOfFirstThoracicVertebra[1..*] :> directRightOfFeatures;
        ref part directRightOfEndothoracicFascia : EndothoracicFascia[1..*] :> directRightOfFeatures;
        ref part medialToEndothoracicFascia : EndothoracicFascia[1..*] :> medialToFeatures;
    }

    part def <fma52530> T2SegmentOfEsophagus :> VertebralSegmentOfEsophagus {
        ref part medialToT2PartOfThoracicDuct : T2PartOfThoracicDuct[1..*] :> medialToFeatures;
        ref part posteriorToRightRecurrentLaryngealNerve : RightRecurrentLaryngealNerve[1..*] :> posteriorToFeatures;
        ref part posteriorToT2SegmentOfTrachea : T2SegmentOfTrachea[1..*] :> posteriorToFeatures;
        ref part directLeftOfRightRecurrentLaryngealNerve : RightRecurrentLaryngealNerve[1..*] :> directLeftOfFeatures;
        ref part directRightOfLeftRecurrentLaryngealNerve : LeftRecurrentLaryngealNerve[1..*] :> directRightOfFeatures;
        ref part posteriorToLeftRecurrentLaryngealNerve : LeftRecurrentLaryngealNerve[1..*] :> posteriorToFeatures;
        ref part directRightOfT2PartOfThoracicDuct : T2PartOfThoracicDuct[1..*] :> directRightOfFeatures;
        ref part directLeftOfEndothoracicFascia : EndothoracicFascia[1..*] :> directLeftOfFeatures;
        ref part directRightOfEndothoracicFascia : EndothoracicFascia[1..*] :> directRightOfFeatures;
        ref part containedInSuperiorMediastinalSpace : SuperiorMediastinalSpace[1..*] :> containedInFeatures;
        ref part anteriorToT2SegmentOfAnteriorLongitudinalLigament : T2SegmentOfAnteriorLongitudinalLigament[1..*] :> anteriorToFeatures;
        ref part surroundedByEndothoracicFascia : EndothoracicFascia[1..*] :> surroundedByFeatures;
        ref part medialToEndothoracicFascia : EndothoracicFascia[1..*] :> medialToFeatures;
    }

    part def <fma52527> T3SegmentOfEsophagus :> VertebralSegmentOfEsophagus {
        ref part anteriorToT3SegmentOfAnteriorLongitudinalLigament : T3SegmentOfAnteriorLongitudinalLigament[1..*] :> anteriorToFeatures;
        ref part directRightOfLeftMediastinalPleura : LeftMediastinalPleura[1..*] :> directRightOfFeatures;
        ref part medialToLeftMediastinalPleura : LeftMediastinalPleura[1..*] :> medialToFeatures;
        ref part medialToEndothoracicFascia : EndothoracicFascia[1..*] :> medialToFeatures;
        ref part directRightOfLeftSubclavianArtery : LeftSubclavianArtery[1..*] :> directRightOfFeatures;
        ref part anteriorToT3PartOfThoracicDuct : T3PartOfThoracicDuct[1..*] :> anteriorToFeatures;
        ref part containedInSuperiorMediastinalSpace : SuperiorMediastinalSpace[1..*] :> containedInFeatures;
        ref part directRightOfLeftRecurrentLaryngealNerve : LeftRecurrentLaryngealNerve[1..*] :> directRightOfFeatures;
        ref part posteriorToLeftSubclavianArtery : LeftSubclavianArtery[1..*] :> posteriorToFeatures;
        ref part posteriorToLeftRecurrentLaryngealNerve : LeftRecurrentLaryngealNerve[1..*] :> posteriorToFeatures;
        ref part directRightOfT3PartOfThoracicDuct : T3PartOfThoracicDuct[1..*] :> directRightOfFeatures;
        ref part directLeftOfT3SegmentOfTrachea : T3SegmentOfTrachea[1..*] :> directLeftOfFeatures;
        ref part posteriorToT3SegmentOfTrachea : T3SegmentOfTrachea[1..*] :> posteriorToFeatures;
        ref part directLeftOfEndothoracicFascia : EndothoracicFascia[1..*] :> directLeftOfFeatures;
    }

    part def <fma52531> T4SegmentOfEsophagus :> VertebralSegmentOfEsophagus {
        ref part directLeftOfT4SegmentOfTrachea : T4SegmentOfTrachea[1..*] :> directLeftOfFeatures;
        ref part anteriorToT4SegmentOfAnteriorLongitudinalLigament : T4SegmentOfAnteriorLongitudinalLigament[1..*] :> anteriorToFeatures;
        ref part directRightOfT4PartOfThoracicDuct : T4PartOfThoracicDuct[1..*] :> directRightOfFeatures;
        ref part directLeftOfRightVagusNerve : RightVagusNerve[1..*] :> directLeftOfFeatures;
        ref part medialToArchOfAorta : ArchOfAorta[1..*] :> medialToFeatures;
        ref part medialToRightVagusNerve : RightVagusNerve[1..*] :> medialToFeatures;
        ref part medialToT4PartOfAzygosVein : T4PartOfAzygosVein[1..*] :> medialToFeatures;
        ref part containedInSuperiorMediastinalSpace : SuperiorMediastinalSpace[1..*] :> containedInFeatures;
        ref part anteriorToT4PartOfThoracicDuct : T4PartOfThoracicDuct[1..*] :> anteriorToFeatures;
        ref part directLeftOfT4PartOfAzygosVein : T4PartOfAzygosVein[1..*] :> directLeftOfFeatures;
        ref part directRightOfArchOfAorta : ArchOfAorta[1..*] :> directRightOfFeatures;
        ref part directRightOfLeftRecurrentLaryngealNerve : LeftRecurrentLaryngealNerve[1..*] :> directRightOfFeatures;
        ref part posteriorToArchOfAorta : ArchOfAorta[1..*] :> posteriorToFeatures;
        ref part posteriorToT4SegmentOfTrachea : T4SegmentOfTrachea[1..*] :> posteriorToFeatures;
        ref part posteriorToLeftRecurrentLaryngealNerve : LeftRecurrentLaryngealNerve[1..*] :> posteriorToFeatures;
    }

    part def <fma52532> T5SegmentOfEsophagus :> VertebralSegmentOfEsophagus {
        ref part directLeftOfT5PartOfRightMainBronchus : T5PartOfRightMainBronchus[1..*] :> directLeftOfFeatures;
        ref part anteriorToT5PartOfAzygosVein : T5PartOfAzygosVein[1..*] :> anteriorToFeatures;
        ref part anteriorToT5PartOfThoracicAorta : T5PartOfThoracicAorta[1..*] :> anteriorToFeatures;
        ref part directRightOfT5PartOfThoracicAorta : T5PartOfThoracicAorta[1..*] :> directRightOfFeatures;
        ref part containedInPosteriorMediastinalSpace : PosteriorMediastinalSpace[1..*] :> containedInFeatures;
        ref part medialToT5PartOfThoracicAorta : T5PartOfThoracicAorta[1..*] :> medialToFeatures;
        ref part directRightOfT5PartOfLeftMainBronchus : T5PartOfLeftMainBronchus[1..*] :> directRightOfFeatures;
        ref part directLeftOfT5PartOfAzygosVein : T5PartOfAzygosVein[1..*] :> directLeftOfFeatures;
        ref part posteriorToT5PartOfLeftMainBronchus : T5PartOfLeftMainBronchus[1..*] :> posteriorToFeatures;
        ref part medialToRightVagusNerve : RightVagusNerve[1..*] :> medialToFeatures;
        ref part directLeftOfRightVagusNerve : RightVagusNerve[1..*] :> directLeftOfFeatures;
        ref part posteriorToT5PartOfRightMainBronchus : T5PartOfRightMainBronchus[1..*] :> posteriorToFeatures;
        ref part anteriorToBodyOfFifthThoracicVertebra : BodyOfFifthThoracicVertebra[1..*] :> anteriorToFeatures;
    }

    part def <fma52533> T6SegmentOfEsophagus :> VertebralSegmentOfEsophagus {
        ref part containedInPosteriorMediastinalSpace : PosteriorMediastinalSpace[1..*] :> containedInFeatures;
        ref part directRightOfT6PartOfThoracicDuct : T6PartOfThoracicDuct[1..*] :> directRightOfFeatures;
        ref part directRightOfEndothoracicFascia : EndothoracicFascia[1..*] :> directRightOfFeatures;
        ref part posteriorToAnteriorEsophagealNervePlexus : AnteriorEsophagealNervePlexus[1..*] :> posteriorToFeatures;
        ref part medialToEndothoracicFascia : EndothoracicFascia[1..*] :> medialToFeatures;
        ref part directRightOfAnteriorEsophagealNervePlexus : AnteriorEsophagealNervePlexus[1..*] :> directRightOfFeatures;
        ref part directLeftOfT6PartOfAzygosVein : T6PartOfAzygosVein[1..*] :> directLeftOfFeatures;
        ref part directRightOfT6PartOfThoracicAorta : T6PartOfThoracicAorta[1..*] :> directRightOfFeatures;
        ref part directLeftOfAnteriorEsophagealNervePlexus : AnteriorEsophagealNervePlexus[1..*] :> directLeftOfFeatures;
        ref part anteriorToT6PartOfThoracicDuct : T6PartOfThoracicDuct[1..*] :> anteriorToFeatures;
        ref part anteriorToT6PartOfThoracicAorta : T6PartOfThoracicAorta[1..*] :> anteriorToFeatures;
        ref part directLeftOfRightMediastinalPleura : RightMediastinalPleura[1..*] :> directLeftOfFeatures;
        ref part posteriorToFibrousPericardium : FibrousPericardium[1..*] :> posteriorToFeatures;
        ref part medialToRightMediastinalPleura : RightMediastinalPleura[1..*] :> medialToFeatures;
        ref part anteriorToT6PartOfAzygosVein : T6PartOfAzygosVein[1..*] :> anteriorToFeatures;
    }

    part def <fma52534> T7SegmentOfEsophagus :> VertebralSegmentOfEsophagus {
        ref part directRightOfEsophagealNervePlexus : EsophagealNervePlexus[1..*] :> directRightOfFeatures;
        ref part anteriorToT7PartOfThoracicDuct : T7PartOfThoracicDuct[1..*] :> anteriorToFeatures;
        ref part containedInPosteriorMediastinalSpace : PosteriorMediastinalSpace[1..*] :> containedInFeatures;
        ref part directRightOfT7PartOfFibrousPericardium : T7PartOfFibrousPericardium[1..*] :> directRightOfFeatures;
        ref part anteriorToT7PartOfAzygosVein : T7PartOfAzygosVein[1..*] :> anteriorToFeatures;
        ref part medialToEsophagealNervePlexus : EsophagealNervePlexus[1..*] :> medialToFeatures;
        ref part posteriorToT7PartOfFibrousPericardium : T7PartOfFibrousPericardium[1..*] :> posteriorToFeatures;
        ref part anteriorToT7PartOfThoracicAorta : T7PartOfThoracicAorta[1..*] :> anteriorToFeatures;
        ref part directLeftOfT7PartOfFibrousPericardium : T7PartOfFibrousPericardium[1..*] :> directLeftOfFeatures;
        ref part medialToRightMediastinalPleura : RightMediastinalPleura[1..*] :> medialToFeatures;
        ref part directLeftOfT7PartOfAzygosVein : T7PartOfAzygosVein[1..*] :> directLeftOfFeatures;
        ref part directLeftOfRightMediastinalPleura : RightMediastinalPleura[1..*] :> directLeftOfFeatures;
        ref part directRightOfT7PartOfThoracicAorta : T7PartOfThoracicAorta[1..*] :> directRightOfFeatures;
    }

    part def <fma61768> T8SegmentOfEsophagus :> VertebralSegmentOfEsophagus {
        doc /* Segment of esophagus at the level of T8 vertebra. */
        ref part medialToEndothoracicFascia : EndothoracicFascia[1..*] :> medialToFeatures;
        ref part directRightOfEndothoracicFascia : EndothoracicFascia[1..*] :> directRightOfFeatures;
        ref part directRightOfT8PartOfThoracicAorta : T8PartOfThoracicAorta[1..*] :> directRightOfFeatures;
        ref part anteriorToT8PartOfThoracicAorta : T8PartOfThoracicAorta[1..*] :> anteriorToFeatures;
        ref part anteriorToEndothoracicFascia : EndothoracicFascia[1..*] :> anteriorToFeatures;
        ref part surroundedByEsophagealNervePlexus : EsophagealNervePlexus[1..*] :> surroundedByFeatures;
        ref part anteriorToT8PartOfThoracicDuct : T8PartOfThoracicDuct[1..*] :> anteriorToFeatures;
        ref part containedInPosteriorMediastinalSpace : PosteriorMediastinalSpace[1..*] :> containedInFeatures;
        ref part directLeftOfT8PartOfThoracicDuct : T8PartOfThoracicDuct[1..*] :> directLeftOfFeatures;
        ref part directLeftOfRightMediastinalPleura : RightMediastinalPleura[1..*] :> directLeftOfFeatures;
        ref part anteriorToBodyOfEighthThoracicVertebra : BodyOfEighthThoracicVertebra[1..*] :> anteriorToFeatures;
        ref part medialToRightMediastinalPleura : RightMediastinalPleura[1..*] :> medialToFeatures;
        ref part directLeftOfEndothoracicFascia : EndothoracicFascia[1..*] :> directLeftOfFeatures;
        ref part directLeftOfT8PartOfAzygosVein : T8PartOfAzygosVein[1..*] :> directLeftOfFeatures;
        ref part anteriorToT8PartOfAzygosVein : T8PartOfAzygosVein[1..*] :> anteriorToFeatures;
        ref part posteriorToT8PartOfFibrousPericardium : T8PartOfFibrousPericardium[1..*] :> posteriorToFeatures;
    }

    part def <fma52536> T9SegmentOfEsophagus :> VertebralSegmentOfEsophagus {
        ref part directLeftOfT9PartOfFibrousPericardium : T9PartOfFibrousPericardium[1..*] :> directLeftOfFeatures;
        ref part containedInPosteriorMediastinalSpace : PosteriorMediastinalSpace[1..*] :> containedInFeatures;
        ref part directRightOfLeftMediastinalPleura : LeftMediastinalPleura[1..*] :> directRightOfFeatures;
        ref part medialToLeftMediastinalPleura : LeftMediastinalPleura[1..*] :> medialToFeatures;
        ref part directLeftOfT9PartOfThoracicAorta : T9PartOfThoracicAorta[1..*] :> directLeftOfFeatures;
        ref part posteriorToT9PartOfFibrousPericardium : T9PartOfFibrousPericardium[1..*] :> posteriorToFeatures;
        ref part anteriorToT9PartOfThoracicAorta : T9PartOfThoracicAorta[1..*] :> anteriorToFeatures;
        ref part directRightOfT9PartOfFibrousPericardium : T9PartOfFibrousPericardium[1..*] :> directRightOfFeatures;
        ref part directRightOfT9PartOfThoracicAorta : T9PartOfThoracicAorta[1..*] :> directRightOfFeatures;
        ref part medialToRightMediastinalPleura : RightMediastinalPleura[1..*] :> medialToFeatures;
        ref part directLeftOfRightMediastinalPleura : RightMediastinalPleura[1..*] :> directLeftOfFeatures;
    }

    part def <fma9396> ThoracicPartOfEsophagus :> SegmentOfEsophagus {
        doc /* Zone of esophagus located in the thorax. */
        part t4SegmentOfEsophagus : T4SegmentOfEsophagus[1..*] :> regionalPartFeatures;
        part t5SegmentOfEsophagus : T5SegmentOfEsophagus[1..*] :> regionalPartFeatures;
        part t6SegmentOfEsophagus : T6SegmentOfEsophagus[1..*] :> regionalPartFeatures;
        ref part continuousWithAbdominalPartOfEsophagus : AbdominalPartOfEsophagus[1..*] :> continuousWithFeatures;
        part posteriorMediastinalSegmentOfEsophagus : PosteriorMediastinalSegmentOfEsophagus[1..*] :> regionalPartFeatures;
        ref part inferiorToCervicalPartOfEsophagus : CervicalPartOfEsophagus[1..*] :> inferiorToFeatures;
        part t3SegmentOfEsophagus : T3SegmentOfEsophagus[1..*] :> regionalPartFeatures;
        part superiorMediastinalSegmentOfEsophagus : SuperiorMediastinalSegmentOfEsophagus[1..*] :> regionalPartFeatures;
        part wallOfThoracicPartOfEsophagus : WallOfThoracicPartOfEsophagus[1..*] :> constitutionalPartFeatures;
        part t8SegmentOfEsophagus : T8SegmentOfEsophagus[1..*] :> regionalPartFeatures;
        part t9SegmentOfEsophagus : T9SegmentOfEsophagus[1..*] :> regionalPartFeatures;
        ref part boundedBySurfaceOfThoracicPartOfEsophagus : SurfaceOfThoracicPartOfEsophagus[1..*] :> boundedByFeatures;
        ref part lymphaticDrainageLeftBronchomediastinalLymphaticTree : LeftBronchomediastinalLymphaticTree[1..*] :> lymphaticDrainageFeatures;
        part t2SegmentOfEsophagus : T2SegmentOfEsophagus[1..*] :> regionalPartFeatures;
        part lumenOfThoracicPartOfEsophagus : LumenOfThoracicPartOfEsophagus[1..*] :> constitutionalPartFeatures;
        ref part continuousWithCervicalPartOfEsophagus : CervicalPartOfEsophagus[1..*] :> continuousWithFeatures;
        ref part superiorToAbdominalPartOfEsophagus : AbdominalPartOfEsophagus[1..*] :> superiorToFeatures;
        ref part lymphaticDrainagePosteriorMediastinalLymphaticChain : PosteriorMediastinalLymphaticChain[1..*] :> lymphaticDrainageFeatures;
        part t7SegmentOfEsophagus : T7SegmentOfEsophagus[1..*] :> regionalPartFeatures;
        part t10SegmentOfEsophagus : T10SegmentOfEsophagus[1..*] :> regionalPartFeatures;
        part t1SegmentOfEsophagus : T1SegmentOfEsophagus[1..*] :> regionalPartFeatures;
    }
    part def <fma14546> TransverseColon :> SegmentOfColon;

    part def <fma14129> WallOfAbdominalPartOfEsophagus :> RegionOfWallOfEsophagus {
        part mucosaOfAbdominalPartOfEsophagus : MucosaOfAbdominalPartOfEsophagus[1..*] :> constitutionalPartFeatures;
        part submucosaOfAbdominalPartOfEsophagus : SubmucosaOfAbdominalPartOfEsophagus[1..*] :> constitutionalPartFeatures;
        part circularMuscleLayerOfAbdominalPartOfEsophagus : CircularMuscleLayerOfAbdominalPartOfEsophagus[1..*] :> regionalPartFeatures;
        part serosaOfEsophagus : SerosaOfEsophagus[1..*] :> regionalPartFeatures;
        part longitudinalMuscleLayerOfAbdominalPartOfEsophagus : LongitudinalMuscleLayerOfAbdominalPartOfEsophagus[1..*] :> regionalPartFeatures;
        ref part continuousWithLumenOfCardiaOfStomach : LumenOfCardiaOfStomach[1..*] :> continuousWithFeatures;
        ref part continuousWithWallOfThoracicPartOfEsophagus : WallOfThoracicPartOfEsophagus[1..*] :> continuousWithFeatures;
    }

    part def <fma17173> WallOfAscendingPartOfDuodenum :> RegionOfWallOfDuodenum_fma86109 {
        part subserosaOfAscendingPartOfDuodenum : SubserosaOfAscendingPartOfDuodenum[1..*] :> constitutionalPartFeatures;
        part muscleLayerOfAscendingPartOfDuodenum : MuscleLayerOfAscendingPartOfDuodenum[1..*] :> constitutionalPartFeatures;
        part posteriorWallOfAscendingPartOfDuodenum : PosteriorWallOfAscendingPartOfDuodenum[1..*] :> regionalPartFeatures;
        part serosaOfAscendingPartOfDuodenum : SerosaOfAscendingPartOfDuodenum[1..*] :> constitutionalPartFeatures;
        part submucosaOfAscendingPartOfDuodenum : SubmucosaOfAscendingPartOfDuodenum[1..*] :> constitutionalPartFeatures;
        part anteriorWallOfAscendingPartOfDuodenum : AnteriorWallOfAscendingPartOfDuodenum[1..*] :> regionalPartFeatures;
        part mucosaOfAscendingPartOfDuodenum : MucosaOfAscendingPartOfDuodenum[1..*] :> constitutionalPartFeatures;
    }

    part def <fma17049> WallOfBodyOfStomach :> RegionOfWallOfStomach {
        part serosaOfBodyOfStomach : SerosaOfBodyOfStomach[1..*] :> regionalPartFeatures;
        part anteriorWallOfBodyOfStomach : AnteriorWallOfBodyOfStomach[1..*] :> regionalPartFeatures;
        part submucosaOfBodyOfStomach : SubmucosaOfBodyOfStomach[1..*] :> constitutionalPartFeatures;
        part muscleLayerOfBodyOfStomach : MuscleLayerOfBodyOfStomach[1..*] :> regionalPartFeatures;
        part subserosaOfBodyOfStomach : SubserosaOfBodyOfStomach[1..*] :> regionalPartFeatures;
        part mucosaOfBodyOfStomach : MucosaOfBodyOfStomach[1..*] :> constitutionalPartFeatures;
        part posteriorWallOfBodyOfStomach : PosteriorWallOfBodyOfStomach[1..*] :> regionalPartFeatures;
    }

    part def <fma17436> WallOfCardiaOfStomach :> RegionOfWallOfStomach {
        part muscleLayerOfCardiaOfStomach : MuscleLayerOfCardiaOfStomach[1..*] :> regionalPartFeatures;
        part serosaOfCardiaOfStomach : SerosaOfCardiaOfStomach[1..*] :> regionalPartFeatures;
        part mucosaOfCardiaOfStomach : MucosaOfCardiaOfStomach[1..*] :> constitutionalPartFeatures;
        part anteriorWallOfCardiaOfStomach : AnteriorWallOfCardiaOfStomach[1..*] :> regionalPartFeatures;
        part subserosaOfCardiaOfStomach : SubserosaOfCardiaOfStomach[1..*] :> regionalPartFeatures;
        part submucosaOfCardiaOfStomach : SubmucosaOfCardiaOfStomach[1..*] :> constitutionalPartFeatures;
        part posteriorWallOfCardiaOfStomach : PosteriorWallOfCardiaOfStomach[1..*] :> regionalPartFeatures;
    }

    part def <fma14127> WallOfCervicalPartOfEsophagus :> RegionOfWallOfEsophagus {
        part submucosaOfCervicalPartOfEsophagus : SubmucosaOfCervicalPartOfEsophagus[1..*] :> constitutionalPartFeatures;
        part mucosaOfCervicalPartOfEsophagus : MucosaOfCervicalPartOfEsophagus[1..*] :> constitutionalPartFeatures;
        part circularMuscleLayerOfCervicalPartOfEsophagus : CircularMuscleLayerOfCervicalPartOfEsophagus[1..*] :> regionalPartFeatures;
        ref part continuousWithWallOfThoracicPartOfEsophagus : WallOfThoracicPartOfEsophagus[1..*] :> continuousWithFeatures;
        part adventitiaOfCervicalPartOfEsophagus : AdventitiaOfCervicalPartOfEsophagus[1..*] :> regionalPartFeatures;
        part longitudinalMuscleLayerOfCervicalPartOfEsophagus : LongitudinalMuscleLayerOfCervicalPartOfEsophagus[1..*] :> regionalPartFeatures;
    }

    part def <fma17171> WallOfDescendingPartOfDuodenum :> RegionOfWallOfDuodenum_fma86109 {
        part posteriorWallOfDescendingPartOfDuodenum : PosteriorWallOfDescendingPartOfDuodenum[1..*] :> regionalPartFeatures;
        part minorDuodenalPapilla : MinorDuodenalPapilla[1..*] :> regionalPartFeatures;
        part muscleLayerOfDescendingPartOfDuodenum : MuscleLayerOfDescendingPartOfDuodenum[1..*] :> constitutionalPartFeatures;
        part subserosaOfDescendingPartOfDuodenum : SubserosaOfDescendingPartOfDuodenum[1..*] :> constitutionalPartFeatures;
        part anteriorWallOfDescendingPartOfDuodenum : AnteriorWallOfDescendingPartOfDuodenum[1..*] :> regionalPartFeatures;
        part submucosaOfDescendingPartOfDuodenum : SubmucosaOfDescendingPartOfDuodenum[1..*] :> constitutionalPartFeatures;
        part serosaOfDescendingPartOfDuodenum : SerosaOfDescendingPartOfDuodenum[1..*] :> constitutionalPartFeatures;
        part majorDuodenalPapilla : MajorDuodenalPapilla[1..*] :> regionalPartFeatures;
        part mucosaOfDescendingPartOfDuodenum : MucosaOfDescendingPartOfDuodenum[1..*] :> constitutionalPartFeatures;
    }

    part def <fma17177> WallOfDistalPartOfJejunum :> RegionOfWallOfJejunum {
        part subserosaOfDistalPartOfJejunum : SubserosaOfDistalPartOfJejunum[1..*] :> constitutionalPartFeatures;
        part submucosaOfDistalPartOfJejunum : SubmucosaOfDistalPartOfJejunum[1..*] :> constitutionalPartFeatures;
        part muscleLayerOfDistalPartOfJejunum : MuscleLayerOfDistalPartOfJejunum[1..*] :> constitutionalPartFeatures;
        part serosaOfDistalPartOfJejunum : SerosaOfDistalPartOfJejunum[1..*] :> constitutionalPartFeatures;
        part anteriorWallOfDistalPartOfJejunum : AnteriorWallOfDistalPartOfJejunum[1..*] :> regionalPartFeatures;
        part mucosaOfDistalPartOfJejunum : MucosaOfDistalPartOfJejunum[1..*] :> constitutionalPartFeatures;
        part posteriorWallOfDistalPartOfJejunum : PosteriorWallOfDistalPartOfJejunum[1..*] :> regionalPartFeatures;
    }

    part def <fma14616> WallOfDuodenum :> RegionOfWallOfSmallIntestine {
        part submucosaOfDuodenum : SubmucosaOfDuodenum[1..*] :> constitutionalPartFeatures;
        part wallOfAscendingPartOfDuodenum : WallOfAscendingPartOfDuodenum[1..*] :> regionalPartFeatures;
        part anteriorWallOfDuodenum : AnteriorWallOfDuodenum[1..*] :> regionalPartFeatures;
        part wallOfDescendingPartOfDuodenum : WallOfDescendingPartOfDuodenum[1..*] :> regionalPartFeatures;
        part mucosaOfDuodenum : MucosaOfDuodenum[1..*] :> constitutionalPartFeatures;
        part muscleLayerOfDuodenum : MuscleLayerOfDuodenum[1..*] :> constitutionalPartFeatures;
        part wallOfHorizontalPartOfDuodenum : WallOfHorizontalPartOfDuodenum[1..*] :> regionalPartFeatures;
        part subserosaOfDuodenum : SubserosaOfDuodenum[1..*] :> constitutionalPartFeatures;
        part wallOfSuperiorPartOfDuodenum : WallOfSuperiorPartOfDuodenum[1..*] :> regionalPartFeatures;
        part serosaOfDuodenum : SerosaOfDuodenum[1..*] :> constitutionalPartFeatures;
        part posteriorWallOfDuodenum : PosteriorWallOfDuodenum[1..*] :> regionalPartFeatures;
    }

    part def <fma12611> WallOfEsophagus :> WallOfOrgan {
        ref part continuousWithWallOfStomach : WallOfStomach[1..*] :> continuousWithFeatures;
        part adventitiaOfEsophagus : AdventitiaOfEsophagus[1..*] :> constitutionalPartFeatures;
        ref part boundedByExternalSurfaceOfEsophagus : ExternalSurfaceOfEsophagus[1..*] :> boundedByFeatures;
        part wallOfThoracicPartOfEsophagus : WallOfThoracicPartOfEsophagus[1..*] :> regionalPartFeatures;
        part wallOfCervicalPartOfEsophagus : WallOfCervicalPartOfEsophagus[1..*] :> regionalPartFeatures;
        part mucosaOfEsophagus : MucosaOfEsophagus[1..*] :> constitutionalPartFeatures;
        ref part continuousWithWallOfPharynx : WallOfPharynx[1..*] :> continuousWithFeatures;
        part muscleLayerOfEsophagus : MuscleLayerOfEsophagus[1..*] :> constitutionalPartFeatures;
        part wallOfAbdominalPartOfEsophagus : WallOfAbdominalPartOfEsophagus[1..*] :> regionalPartFeatures;
        part submucosaOfEsophagus : SubmucosaOfEsophagus[1..*] :> constitutionalPartFeatures;
        ref part boundedByInternalSurfaceOfEsophagus : InternalSurfaceOfEsophagus[1..*] :> boundedByFeatures;
        part serosaOfEsophagus : SerosaOfEsophagus[1..*] :> constitutionalPartFeatures;
    }

    part def <fma17048> WallOfFundusOfStomach :> RegionOfWallOfStomach {
        part submucosaOfFundusOfStomach : SubmucosaOfFundusOfStomach[1..*] :> constitutionalPartFeatures;
        part serosaOfFundusOfStomach : SerosaOfFundusOfStomach[1..*] :> regionalPartFeatures;
        part anteriorWallOfFundusOfStomach : AnteriorWallOfFundusOfStomach[1..*] :> regionalPartFeatures;
        part subserosaOfFundusOfStomach : SubserosaOfFundusOfStomach[1..*] :> regionalPartFeatures;
        part mucosaOfFundusOfStomach : MucosaOfFundusOfStomach[1..*] :> constitutionalPartFeatures;
        part posteriorWallOfFundusOfStomach : PosteriorWallOfFundusOfStomach[1..*] :> regionalPartFeatures;
        part muscleLayerOfFundusOfStomach : MuscleLayerOfFundusOfStomach[1..*] :> regionalPartFeatures;
    }

    part def <fma17172> WallOfHorizontalPartOfDuodenum :> RegionOfWallOfDuodenum_fma86109 {
        part muscleLayerOfHorizontalPartOfDuodenum : MuscleLayerOfHorizontalPartOfDuodenum[1..*] :> constitutionalPartFeatures;
        part posteriorWallOfHorizontalPartOfDuodenum : PosteriorWallOfHorizontalPartOfDuodenum[1..*] :> regionalPartFeatures;
        part subserosaOfHorizontalPartOfDuodenum : SubserosaOfHorizontalPartOfDuodenum[1..*] :> constitutionalPartFeatures;
        part submucosaOfHorizontalPartOfDuodenum : SubmucosaOfHorizontalPartOfDuodenum[1..*] :> constitutionalPartFeatures;
        part anteriorWallOfHorizontalPartOfDuodenum : AnteriorWallOfHorizontalPartOfDuodenum[1..*] :> regionalPartFeatures;
        part mucosaOfHorizontalPartOfDuodenum : MucosaOfHorizontalPartOfDuodenum[1..*] :> constitutionalPartFeatures;
        part serosaOfHorizontalPartOfDuodenum : SerosaOfHorizontalPartOfDuodenum[1..*] :> constitutionalPartFeatures;
    }

    part def <fma14617> WallOfJejunum :> RegionOfWallOfSmallIntestine {
        part wallOfMiddlePartOfJejunum : WallOfMiddlePartOfJejunum[1..*] :> regionalPartFeatures;
        part submucosaOfJejunum : SubmucosaOfJejunum[1..*] :> constitutionalPartFeatures;
        part subserosaOfJejunum : SubserosaOfJejunum[1..*] :> constitutionalPartFeatures;
        part serosaOfJejunum : SerosaOfJejunum[1..*] :> constitutionalPartFeatures;
        part mucosaOfJejunum : MucosaOfJejunum[1..*] :> constitutionalPartFeatures;
        part wallOfDistalPartOfJejunum : WallOfDistalPartOfJejunum[1..*] :> regionalPartFeatures;
        part muscleLayerOfJejunum : MuscleLayerOfJejunum[1..*] :> constitutionalPartFeatures;
        ref part drainsIntoJuxtaIntestinalLymphNodeGroupOfJejunum : JuxtaIntestinalLymphNodeGroupOfJejunum[1..*] :> drainsIntoFeatures;
        part wallOfProximalPartOfJejunum : WallOfProximalPartOfJejunum[1..*] :> regionalPartFeatures;
    }

    part def <fma17176> WallOfMiddlePartOfJejunum :> RegionOfWallOfJejunum {
        part anteriorWallOfMiddlePartOfJejunum : AnteriorWallOfMiddlePartOfJejunum[1..*] :> regionalPartFeatures;
        part posteriorWallOfMiddlePartOfJejunum : PosteriorWallOfMiddlePartOfJejunum[1..*] :> regionalPartFeatures;
        part mucosaOfMiddlePartOfJejunum : MucosaOfMiddlePartOfJejunum[1..*] :> constitutionalPartFeatures;
        part submucosaOfMiddlePartOfJejunum : SubmucosaOfMiddlePartOfJejunum[1..*] :> constitutionalPartFeatures;
        part muscleLayerOfMiddlePartOfJejunum : MuscleLayerOfMiddlePartOfJejunum[1..*] :> constitutionalPartFeatures;
        part serosaOfMiddlePartOfJejunum : SerosaOfMiddlePartOfJejunum[1..*] :> constitutionalPartFeatures;
        part subserosaOfMiddlePartOfJejunum : SubserosaOfMiddlePartOfJejunum[1..*] :> constitutionalPartFeatures;
    }

    part def <fma17175> WallOfProximalPartOfJejunum :> RegionOfWallOfJejunum {
        part mucosaOfProximalPartOfJejunum : MucosaOfProximalPartOfJejunum[1..*] :> constitutionalPartFeatures;
        part muscleLayerOfProximalPartOfJejunum : MuscleLayerOfProximalPartOfJejunum[1..*] :> constitutionalPartFeatures;
        part subserosaOfProximalPartOfJejunum : SubserosaOfProximalPartOfJejunum[1..*] :> constitutionalPartFeatures;
        part submucosaOfProximalPartOfJejunum : SubmucosaOfProximalPartOfJejunum[1..*] :> constitutionalPartFeatures;
        part anteriorWallOfProximalPartOfJejunum : AnteriorWallOfProximalPartOfJejunum[1..*] :> regionalPartFeatures;
        part posteriorWallOfProximalPartOfJejunum : PosteriorWallOfProximalPartOfJejunum[1..*] :> regionalPartFeatures;
        part serosaOfProximalPartOfJejunum : SerosaOfProximalPartOfJejunum[1..*] :> constitutionalPartFeatures;
    }

    part def <fma17050> WallOfPyloricAntrum :> RegionOfWallOfStomach {
        part posteriorWallOfPyloricAntrum : PosteriorWallOfPyloricAntrum[1..*] :> regionalPartFeatures;
        part submucosaOfPyloricAntrum : SubmucosaOfPyloricAntrum[1..*] :> constitutionalPartFeatures;
        part muscleLayerOfPyloricAntrum : MuscleLayerOfPyloricAntrum[1..*] :> regionalPartFeatures;
        part mucosaOfPyloricAntrum : MucosaOfPyloricAntrum[1..*] :> constitutionalPartFeatures;
        part subserosaOfPyloricAntrum : SubserosaOfPyloricAntrum[1..*] :> regionalPartFeatures;
        part serosaOfPyloricAntrum : SerosaOfPyloricAntrum[1..*] :> regionalPartFeatures;
        part anteriorWallOfPyloricAntrum : AnteriorWallOfPyloricAntrum[1..*] :> regionalPartFeatures;
    }

    part def <fma17051> WallOfPyloricCanal :> RegionOfWallOfStomach {
        part subserosaOfPyloricCanal : SubserosaOfPyloricCanal[1..*] :> regionalPartFeatures;
        part serosaOfPyloricCanal : SerosaOfPyloricCanal[1..*] :> regionalPartFeatures;
        part muscleLayerOfPyloricCanal : MuscleLayerOfPyloricCanal[1..*] :> regionalPartFeatures;
        part anteriorWallOfPyloricCanal : AnteriorWallOfPyloricCanal[1..*] :> regionalPartFeatures;
        part submucosaOfPyloricCanal : SubmucosaOfPyloricCanal[1..*] :> constitutionalPartFeatures;
        part posteriorWallOfPyloricCanal : PosteriorWallOfPyloricCanal[1..*] :> regionalPartFeatures;
        part mucosaOfPyloricCanal : MucosaOfPyloricCanal[1..*] :> constitutionalPartFeatures;
    }

    part def <fma17437> WallOfPylorus :> RegionOfWallOfStomach {
        part subserosaOfPylorus : SubserosaOfPylorus[1..*] :> regionalPartFeatures;
        part mucosaOfPylorus : MucosaOfPylorus[1..*] :> constitutionalPartFeatures;
        part posteriorWallOfPylorus : PosteriorWallOfPylorus[1..*] :> regionalPartFeatures;
        part muscleLayerOfPylorus : MuscleLayerOfPylorus[1..*] :> regionalPartFeatures;
        part submucosaOfPylorus : SubmucosaOfPylorus[1..*] :> constitutionalPartFeatures;
        part serosaOfPylorus : SerosaOfPylorus[1..*] :> regionalPartFeatures;
        part anteriorWallOfPylorus : AnteriorWallOfPylorus[1..*] :> regionalPartFeatures;
    }
    part def <fma14615> WallOfSmallIntestine :> WallOfOrgan;

    part def <fma14582> WallOfStomach :> WallOfOrgan {
        part wallOfFundusOfStomach : WallOfFundusOfStomach[1..*] :> regionalPartFeatures;
        part muscleLayerOfStomach : MuscleLayerOfStomach[1..*] :> constitutionalPartFeatures;
        ref part continuousWithWallOfEsophagus : WallOfEsophagus[1..*] :> continuousWithFeatures;
        part posteriorWallOfStomach : PosteriorWallOfStomach[1..*] :> regionalPartFeatures;
        part serosaOfStomach : SerosaOfStomach[1..*] :> constitutionalPartFeatures;
        part wallOfBodyOfStomach : WallOfBodyOfStomach[1..*] :> regionalPartFeatures;
        part wallOfCardiaOfStomach : WallOfCardiaOfStomach[1..*] :> regionalPartFeatures;
        part wallOfPyloricAntrum : WallOfPyloricAntrum[1..*] :> regionalPartFeatures;
        part wallOfPyloricCanal : WallOfPyloricCanal[1..*] :> regionalPartFeatures;
        part submucosaOfStomach : SubmucosaOfStomach[1..*] :> constitutionalPartFeatures;
        part mucosaOfStomach : MucosaOfStomach[1..*] :> constitutionalPartFeatures;
        part anteriorWallOfStomach : AnteriorWallOfStomach[1..*] :> regionalPartFeatures;
        part wallOfPylorus : WallOfPylorus[1..*] :> regionalPartFeatures;
        ref part continuousWithWallOfSmallIntestine : WallOfSmallIntestine[1..*] :> continuousWithFeatures;
        part subserosaOfStomach : SubserosaOfStomach[1..*] :> constitutionalPartFeatures;
    }

    part def <fma17170> WallOfSuperiorPartOfDuodenum :> RegionOfWallOfDuodenum_fma86109 {
        part muscleLayerOfSuperiorPartOfDuodenum : MuscleLayerOfSuperiorPartOfDuodenum[1..*] :> constitutionalPartFeatures;
        part subserosaOfSuperiorPartOfDuodenum : SubserosaOfSuperiorPartOfDuodenum[1..*] :> constitutionalPartFeatures;
        part posteriorWallOfSuperiorPartOfDuodenum : PosteriorWallOfSuperiorPartOfDuodenum[1..*] :> regionalPartFeatures;
        part anteriorWallOfSuperiorPartOfDuodenum : AnteriorWallOfSuperiorPartOfDuodenum[1..*] :> regionalPartFeatures;
        part serosaOfSuperiorPartOfDuodenum : SerosaOfSuperiorPartOfDuodenum[1..*] :> constitutionalPartFeatures;
        part submucosaOfSuperiorPartOfDuodenum : SubmucosaOfSuperiorPartOfDuodenum[1..*] :> constitutionalPartFeatures;
        part mucosaOfSuperiorPartOfDuodenum : MucosaOfSuperiorPartOfDuodenum[1..*] :> constitutionalPartFeatures;
    }

    part def <fma14128> WallOfThoracicPartOfEsophagus :> RegionOfWallOfEsophagus {
        part circularMuscleLayerOfThoracicPartOfEsophagus : CircularMuscleLayerOfThoracicPartOfEsophagus[1..*] :> regionalPartFeatures;
        part adventitiaOfThoracicPartOfEsophagus : AdventitiaOfThoracicPartOfEsophagus[1..*] :> regionalPartFeatures;
        part mucosaOfThoracicPartOfEsophagus : MucosaOfThoracicPartOfEsophagus[1..*] :> constitutionalPartFeatures;
        part longitudinalMuscleLayerOfThoracicPartOfEsophagus : LongitudinalMuscleLayerOfThoracicPartOfEsophagus[1..*] :> regionalPartFeatures;
        ref part continuousWithWallOfCervicalPartOfEsophagus : WallOfCervicalPartOfEsophagus[1..*] :> continuousWithFeatures;
        ref part continuousWithWallOfAbdominalPartOfEsophagus : WallOfAbdominalPartOfEsophagus[1..*] :> continuousWithFeatures;
        part submucosaOfThoracicPartOfEsophagus : SubmucosaOfThoracicPartOfEsophagus[1..*] :> constitutionalPartFeatures;
    }
}
