// GENERATED by `memo anatomy generate` from the Foundational Model of Anatomy (FMA) 5.1.0,
// University of Washington Structural Informatics Group, http://purl.org/sig/ont/fma.owl, CC BY 4.0, https://creativecommons.org/licenses/by/4.0/.
// Converted from OWL to SysML v2 by MEMO's anatomy extension. Do not edit: change the project's AnatomySelectors and regenerate.
package gastric_bypass_variants_anatomy_fma_core_organ_component_of_lymphatic_tree_organ {
    private import gastric_bypass_variants_anatomy_fma::*;
    part def <fma62835> EsophagealTributaryOfThoracicDuct :> LymphaticVesselOfThorax;

    part def <fma30315> LymphaticVessel :> OrganComponentOfLymphaticTreeOrgan {
        doc /* Organ component of lymphatic tree organ, each instance of which is a tubular segment of some lymphatic chain that collects lymph from some tissue and through some series of vessels and lymph nodes passes the lymph into some bloodstream. */
    }
    part def <fma278543> LymphaticVesselOfThorax :> LymphaticVesselOfTrunk;
    part def <fma278550> LymphaticVesselOfTrunk :> VesselOfLymphaticChain;
    part def <fma278572> OrganComponentOfLymphaticTreeOrgan :> OrganComponent;
    part def <fma14197> VesselOfLymphaticChain :> LymphaticVessel;
}
