// GENERATED by `memo anatomy generate` from the Foundational Model of Anatomy (FMA) 5.1.0,
// University of Washington Structural Informatics Group, http://purl.org/sig/ont/fma.owl, CC BY 4.0, https://creativecommons.org/licenses/by/4.0/.
// Converted from OWL to SysML v2 by MEMO's anatomy extension. Do not edit: change the project's AnatomySelectors and regenerate.
package gastric_bypass_variants_anatomy_fma_nervous_nerve {
    private import gastric_bypass_variants_anatomy_fma::*;
    part def <fma6228> BranchOfVagusNerve :> BranchOfCranialNerve;
    part def <fma78584> GastricBranchOfLeftVagusNerve :> GastricBranchOfVagusNerve;
    part def <fma78583> GastricBranchOfRightVagusNerve :> GastricBranchOfVagusNerve;
    part def <fma78582> GastricBranchOfVagusNerve :> BranchOfVagusNerve;
    part def <fma14469> LeftRecurrentLaryngealNerve :> RecurrentLaryngealNerve;
    part def <fma6246> RecurrentLaryngealNerve :> BranchOfVagusNerve;
    part def <fma14468> RightRecurrentLaryngealNerve :> RecurrentLaryngealNerve;
}
