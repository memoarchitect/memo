// GENERATED by `memo anatomy generate` from the Foundational Model of Anatomy (FMA) 5.1.0,
// University of Washington Structural Informatics Group, http://purl.org/sig/ont/fma.owl, CC BY 4.0, https://creativecommons.org/licenses/by/4.0/.
// Converted from OWL to SysML v2 by MEMO's anatomy extension. Do not edit: change the project's AnatomySelectors and regenerate.
package gastric_bypass_variants_anatomy_fma_core_anatomical_set {
    private import gastric_bypass_variants_anatomy_fma::*;

    part def <fma55652> AnatomicalSet :> MaterialAnatomicalEntity {
        doc /* Material anatomical entity which consists of a maximum number of some instances of discontinuous members of the same class. Examples: set of cranial nerves, ventral branches of aorta, set of mammary arteries, set of thoracic viscera, dentition. */
    }

    part def <fma70776> LymphNodeGroup :> SetOfOrganComponents {
        doc /* Set of organ components of lymphatic tree organ consisting of lymph nodes without connecting lymphatic vessels. */
    }

    part def <fma278485> LymphNodeGroupOfAbdomen :> LymphNodeGroupOfTrunk {
        doc /* Lymph node group which is located in the abdomen. */
    }

    part def <fma71773> LymphNodeGroupOfAbdomenProper :> LymphNodeGroupOfAbdomen {
        doc /* Abdominal lymph node group which is located below the diaphragm and above the plane of pelvic inlet. */
    }
    part def <fma301793> LymphNodeGroupOfBodyProper :> LymphNodeGroup;
    part def <fma301798> LymphNodeGroupOfTrunk :> LymphNodeGroupOfBodyProper;
    part def <fma78561> SetOfOrganComponents :> SetOfOrganParts;

    part def <fma228667> SetOfOrganParts :> AnatomicalSet {
        doc /* Anatomical set which has as its direct members organ parts of same type. */
    }
    part def <fma71786> VisceralLymphNodeGroupOfAbdomenProper :> LymphNodeGroupOfAbdomenProper;
}
