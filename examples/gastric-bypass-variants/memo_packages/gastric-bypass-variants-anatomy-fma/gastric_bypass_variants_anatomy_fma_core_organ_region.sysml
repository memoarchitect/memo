// GENERATED by `memo anatomy generate` from the Foundational Model of Anatomy (FMA) 5.1.0,
// University of Washington Structural Informatics Group, http://purl.org/sig/ont/fma.owl, CC BY 4.0, https://creativecommons.org/licenses/by/4.0/.
// Converted from OWL to SysML v2 by MEMO's anatomy extension. Do not edit: change the project's AnatomySelectors and regenerate.
package gastric_bypass_variants_anatomy_fma_core_organ_region {
    private import gastric_bypass_variants_anatomy_fma::*;

    part def <fma67619> OrganRegion :> CardinalOrganPart {
        doc /* Cardinal organ part, each instance of which is a fiat subdivision of some organ. Examples: lingula of left lung, tail of pancreas, artery, trochanter, nodulus of semilunar valvule, right side of heart, duodenum, fundus of stomach. */
    }
}
