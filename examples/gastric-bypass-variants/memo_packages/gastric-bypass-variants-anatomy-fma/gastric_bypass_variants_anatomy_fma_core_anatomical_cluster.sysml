// GENERATED by `memo anatomy generate` from the Foundational Model of Anatomy (FMA) 5.1.0,
// University of Washington Structural Informatics Group, http://purl.org/sig/ont/fma.owl, CC BY 4.0, https://creativecommons.org/licenses/by/4.0/.
// Converted from OWL to SysML v2 by MEMO's anatomy extension. Do not edit: change the project's AnatomySelectors and regenerate.
package gastric_bypass_variants_anatomy_fma_core_anatomical_cluster {
    private import gastric_bypass_variants_anatomy_fma::*;

    part def <fma49443> AnatomicalCluster :> PostnatalAnatomicalStructure {
        doc /* Postnatal anatomical structure, each instance of which has as it direct parts a heterogeneous collection of some instances of two or more subclasses of anatomcial structure, which are spatially related to one another; the collections as a whole does not satisfy the definition of any other subclass of anatomical structure. Eaxmples: root of lung, back, anatomical snuffbox, motor unit, juxtaglomerular complex. */
    }

    part def <fma5898> AnatomicalJunction :> AnatomicalCluster {
        doc /* Anatomical cluster in which parts of two or more anatomical structures establish physical continuity with one another or intermingle their component parts. Examples: esophagogastric junction, linea alba, knee joint. */
    }
    part def <fma5910> AutonomicNervePlexus :> NervePlexus;
    part def <fma6630> CeliacNervePlexus :> AutonomicNervePlexus;
    part def <fma62811> EpitheliumAssociatedLymphoidTissue :> LymphoidTissue;
    part def <fma6632> HepaticNervePlexus :> AutonomicNervePlexus;

    part def <fma64989> HeterogeneousAnatomicalCluster :> AnatomicalCluster {
        doc /* Anatomical cluster which has as its direct parts all or some members of two or more organ subclasses and one or more organ part subclasses which are grouped together according to some shared attributes. Examples: larynx, internal ear, pharynx. */
    }
    part def <fma61926> IntramuralNervePlexus :> AutonomicNervePlexus;
    part def <fma6633> LeftGastricNervePlexus :> AutonomicNervePlexus;
    part def <fma78581> LeftPhrenicNervePlexus :> PhrenicNervePlexus;
    part def <fma55220> LymphoidTissue :> LymphomyeloidTissue;
    part def <fma79770> LymphomyeloidTissue :> PortionOfHeterogeneousTissue;
    part def <fma62819> MucosaAssociatedLymphoidTissue :> EpitheliumAssociatedLymphoidTissue;

    part def <fma5901> NervePlexus :> AnatomicalJunction {
        doc /* Anatomical junction where subdivisions of two or more neural trees interconnect with one another to form a network through which nerve fibers of the constituent nerve trees become regrouped; together with other nerve plexuses, nerves and ganglia, it constitutes the peripheral nervous system. Examples: cervical nerve plexus, brachial nerve plexus, sacral nerve plexus. */
    }
    part def <fma46688> Pharynx :> HeterogeneousAnatomicalCluster;
    part def <fma78579> PhrenicNervePlexus :> NervePlexus;
    part def <fma62798> PortionOfHeterogeneousTissue :> TissueCluster;
    part def <fma54877> SubdivisionOfPharynx :> HeterogeneousAnatomicalCluster;

    part def <fma62799> TissueCluster :> AnatomicalCluster {
        doc /* Anatomical cluster which has as its direct parts all or some members of two or more tissue types grouped together according to shared attributes. */
    }
    part def <fma55033> WallOfPharynx :> SubdivisionOfPharynx;

    part def <fma11337> ZoneOfContinuity :> AnatomicalJunction {
        doc /* Zone of connectivity where there is no bona fide boundary between some parts of two contiguous structures. */
    }
}
