// GENERATED by `memo anatomy generate` from the Foundational Model of Anatomy (FMA) 5.1.0,
// University of Washington Structural Informatics Group, http://purl.org/sig/ont/fma.owl, CC BY 4.0, https://creativecommons.org/licenses/by/4.0/.
// Converted from OWL to SysML v2 by MEMO's anatomy extension. Do not edit: change the project's AnatomySelectors and regenerate.
package gastric_bypass_variants_anatomy_fma_core_organ {
    private import gastric_bypass_variants_anatomy_fma::*;

    part def <fma55671> CavitatedOrgan :> Organ {
        doc /* Organ, each instance of which has as its direct parts instances of some organ cavity and organ wall. Examples: stomach, urinary bladder, gall bladder. */
    }

    part def <fma5865> CranialNerve :> NeuralTreeOrgan {
        doc /* Neural tree organ which is continuous with the brain. Examples: Trochlear nerve, facial nerve. */
    }

    part def <fma5023> FasciaOrgan :> NonparenchymatousOrgan {
        doc /* Nonparenchymatous organ that consists of organ parts composed of various types of connective tissue; it surrounds and interconnects various organs and body parts, and establishes the anatomical integrity of body parts and organ systems. Examples: superficial fascia, investing fascia, fat pad. */
    }

    part def <fma55664> HomogeneousOrgan :> ParenchymatousOrgan {
        doc /* Parenchymatous organ the stroma of which does not subdivide the parenchyma into distinct morphological organ parts. Examples: parathyroid gland, coccygeal body, right carotid body. */
    }
    part def <fma9634> InternalFascia :> FasciaOrgan;

    part def <fma7145> MembraneOrgan :> NonparenchymatousOrgan {
        doc /* Nonparenchymatous organ that primarily consists of dense connective tissue organized into a sheet which interconnects two or more organs, separates two or more body spaces from one another, or surrounds an organ or body part. Examples: interosseous membrane of forearm, obturator membrane, tympanic membrane, fibrous pericardium, fascia lata, dura mater. */
    }
    part def <fma0329044> MuscleOfBodyProper :> MuscleOrgan;
    part def <fma0329118> MuscleOfThoracicPartOfTrunk :> MuscleOfTrunk;

    part def <fma9619> MuscleOfThorax :> MuscleOfThoracicPartOfTrunk {
        doc /* Muscle organ which is a part of the thorax. Examples: external intercostal muscle, diaphragm. */
    }

    part def <fma58274> MuscleOfTrunk :> MuscleOfBodyProper {
        doc /* Muscle organ which is a part of the trunk. Examples: external intercostal muscle, external oblique, levator ani. */
    }

    part def <fma5022> MuscleOrgan :> NonparenchymatousOrgan {
        doc /* Nonparenchymatous organ that primarily consists of skeletal muscle tissue aggregated into macroscopic fasciculi by connective tissue; together with other muscles, it constitutes the muscular system. Examples: biceps, diaphragm, masseter, right third external intercostal muscle, external oblique, levator ani, serratus anterior. */
    }

    part def <fma61284> NeuralTreeOrgan :> NonparenchymatousOrgan {
        doc /* Nonparenchymatous organ which has as its direct parts an aggregate of neurons, the somas of which are located in the neuraxis and their network of neurites (axons) predominantly located outside the neuraxis. */
    }

    part def <fma55665> NonparenchymatousOrgan :> SolidOrgan {
        doc /* Solid organ which consists of organ parts that are arranged as fascicles or sheets. Examples: muscle organ, ligament organ, membrane organ, skin, viscerocranial mucosa. */
    }

    part def <fma67498> Organ :> PostnatalAnatomicalStructure {
        doc /* Anatomical structure, each instance of which has a maximal complement of instances of two or more types of tissue or one or more types of essential morphologic unit, a predominantly bona fide boundary and intrinsic vasculature and neural network. Examples: liver, lung, kidney, stomach, urinary bladder, gall bladder. */
    }

    part def <fma55672> OrganWithOrganCavity :> CavitatedOrgan {
        doc /* Cavitated organ in which its unshared parts surround one continuous anatomical space. Examples: stomach, urinary bladder, esophagus, uterine tube. */
    }

    part def <fma55661> ParenchymatousOrgan :> SolidOrgan {
        doc /* Solid organ, each instance of which has as its direct parts instances of some parenchyma and connective tissue stroma. Examples: liver, lung, spleen. */
    }

    part def <fma55670> SolidOrgan :> Organ {
        doc /* Organ the direct parts of which consist of either fascicles or sheets or parenchyma and connective tissue stroma. Examples: Examples: muscle organ, ligament organ, membrane organ, skin, viscerocranial mucosa. Old definition: Organ the unshared parts of which do not surround macroscopic anatomical spaces; only its shared parts (subdivisions of hollow tree organs) contain anatomical spaces. Examples: lung, liver, thymus, ovary, muscle organ, superficial fascia, skin. */
    }
}
