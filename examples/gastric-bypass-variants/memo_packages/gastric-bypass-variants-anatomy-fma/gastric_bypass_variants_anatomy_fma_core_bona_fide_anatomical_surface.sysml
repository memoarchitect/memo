// GENERATED by `memo anatomy generate` from the Foundational Model of Anatomy (FMA) 5.1.0,
// University of Washington Structural Informatics Group, http://purl.org/sig/ont/fma.owl, CC BY 4.0, https://creativecommons.org/licenses/by/4.0/.
// Converted from OWL to SysML v2 by MEMO's anatomy extension. Do not edit: change the project's AnatomySelectors and regenerate.
package gastric_bypass_variants_anatomy_fma_core_bona_fide_anatomical_surface {
    private import gastric_bypass_variants_anatomy_fma::*;

    part def <fma242980> BonaFideAnatomicalSurface :> AnatomicalSurface {
        doc /* Anatomical surface which marks a physical discontinuity between two or more anatomical structures or is an interface between an anatomical space and one more anatomical structures. Examples: surface of head, costal surface of lung, luminal surface of epithelium, P-face of plasma membrane. */
    }

    part def <fma24208> SurfaceOfOrgan :> BonaFideAnatomicalSurface {
        doc /* Anatomical surface, which is the internal or external surface of an organ. Examples: surface of heart, internal surface of stomach, surface of skin. */
    }
    part def <fma14567> SurfaceOfStomach :> SurfaceOfOrgan;
}
