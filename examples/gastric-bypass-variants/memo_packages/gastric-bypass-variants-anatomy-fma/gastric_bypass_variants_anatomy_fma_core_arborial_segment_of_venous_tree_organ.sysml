// GENERATED by `memo anatomy generate` from the Foundational Model of Anatomy (FMA) 5.1.0,
// University of Washington Structural Informatics Group, http://purl.org/sig/ont/fma.owl, CC BY 4.0, https://creativecommons.org/licenses/by/4.0/.
// Converted from OWL to SysML v2 by MEMO's anatomy extension. Do not edit: change the project's AnatomySelectors and regenerate.
package gastric_bypass_variants_anatomy_fma_core_arborial_segment_of_venous_tree_organ {
    private import gastric_bypass_variants_anatomy_fma::*;
    part def <fma86188> ArborialSegmentOfVenousTreeOrgan :> SegmentOfBloodVesselTreeOrgan;
    part def <fma62829> EsophagealTributaryOfInferiorThyroidVein :> TributaryOfInferiorThyroidVein;
    part def <fma62831> EsophagealTributaryOfLeftInferiorThyroidVein :> EsophagealTributaryOfInferiorThyroidVein;
    part def <fma62830> EsophagealTributaryOfRightInferiorThyroidVein :> EsophagealTributaryOfInferiorThyroidVein;
    part def <fma66645> PortalVein :> Vein;
    part def <fma77883> SubdivisionOfBrachiocephalicVein :> SubdivisionOfSuperiorSystemicVenousTree;
    part def <fma78048> SubdivisionOfSuperiorSystemicVenousTree :> SystemicVein;

    part def <fma66644> SystemicVein :> Vein {
        doc /* Vein in the systemic venous system. */
    }
    part def <fma14294> TributaryOfAzygosVein :> SubdivisionOfSuperiorSystemicVenousTree;
    part def <fma62828> TributaryOfInferiorThyroidVein :> SubdivisionOfBrachiocephalicVein;
    part def <fma50736> TributaryOfPreHepaticPortalVein :> PortalVein;
    part def <fma15387> TributaryOfSplenicVein :> TributaryOfPreHepaticPortalVein;
    part def <fma15396> TributaryOfSuperiorMesentericVein :> TributaryOfPreHepaticPortalVein;
    part def <fma50723> Vein :> ArborialSegmentOfVenousTreeOrgan;
}
