// GENERATED by `memo anatomy generate` from the Foundational Model of Anatomy (FMA) 5.1.0,
// University of Washington Structural Informatics Group, http://purl.org/sig/ont/fma.owl, CC BY 4.0, https://creativecommons.org/licenses/by/4.0/.
// Converted from OWL to SysML v2 by MEMO's anatomy extension. Do not edit: change the project's AnatomySelectors and regenerate.
package gastric_bypass_variants_anatomy_fma_core_surface_of_organ_region {
    private import gastric_bypass_variants_anatomy_fma::*;
    part def <fma17334> ExternalSurfaceOfSubdivisionOfSmallIntestine :> SurfaceOfRegionOfSmallIntestine;
    part def <fma20028> InternalSurfaceOfAnteriorWallOfSubdivisionOfStomach :> InternalSurfaceOfSubdivisionOfStomach;
    part def <fma20029> InternalSurfaceOfPosteriorWallOfSubdivisionOfStomach :> InternalSurfaceOfSubdivisionOfStomach;
    part def <fma20025> InternalSurfaceOfSegmentOfDuodenum :> ExternalSurfaceOfSubdivisionOfSmallIntestine;
    part def <fma17094> InternalSurfaceOfSubdivisionOfStomach :> SurfaceOfRegionOfStomach;

    part def <fma45688> SurfaceOfOrganRegion :> BonaFideAnatomicalSurface {
        doc /* Anatomical surface, which is the external surface of a subdivision of a solid organ or the external or internal surface of a subdivision of a cavitated organ. Examples: surface of cervical part of esophagus, surface of body of vertebra, internal surface of fundus of stomach. */
    }
    part def <fma17247> SurfaceOfRegionOfSmallIntestine :> SurfaceOfOrganRegion;
    part def <fma17088> SurfaceOfRegionOfStomach :> SurfaceOfOrganRegion;
    part def <fma45584> SurfaceOfSegmentOfEsophagus :> SurfaceOfOrganRegion;
    part def <fma45586> SurfaceOfThoracicPartOfEsophagus :> SurfaceOfSegmentOfEsophagus;
}
