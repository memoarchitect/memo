// GENERATED by `memo anatomy generate` from the Foundational Model of Anatomy (FMA) 5.1.0,
// University of Washington Structural Informatics Group, http://purl.org/sig/ont/fma.owl, CC BY 4.0, https://creativecommons.org/licenses/by/4.0/.
// Converted from OWL to SysML v2 by MEMO's anatomy extension. Do not edit: change the project's AnatomySelectors and regenerate.
package gastric_bypass_variants_anatomy_fma_nervous_postnatal_anatomical_structure {
    private import gastric_bypass_variants_anatomy_fma::*;
    part def <fma6219> RightVagusNerve :> VagusNerve;
    part def <fma5731> VagusNerve :> CranialNerve;
}
