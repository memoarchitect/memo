// GENERATED by `memo anatomy generate` from the Foundational Model of Anatomy (FMA) 5.1.0,
// University of Washington Structural Informatics Group, http://purl.org/sig/ont/fma.owl, CC BY 4.0, https://creativecommons.org/licenses/by/4.0/.
// Converted from OWL to SysML v2 by MEMO's anatomy extension. Do not edit: change the project's AnatomySelectors and regenerate.
package gastric_bypass_variants_anatomy_fma_respiratory {
    private import gastric_bypass_variants_anatomy_fma::*;
    part def <fma71127> C6SegmentOfTrachea :> VertebralSegmentOfTrachea;
    part def <fma68027> C7SegmentOfTrachea :> VertebralSegmentOfTrachea;
    part def <fma54935> CavityOfPharynx :> AnatomicalConduitSpace;
    part def <fma68021> T1SegmentOfTrachea :> VertebralSegmentOfTrachea;
    part def <fma68022> T2SegmentOfTrachea :> VertebralSegmentOfTrachea;
    part def <fma68023> T3SegmentOfTrachea :> VertebralSegmentOfTrachea;
    part def <fma68024> T4SegmentOfTrachea :> VertebralSegmentOfTrachea;
    part def <fma7394> Trachea :> SegmentOfTracheobronchialTree;
}
