// GENERATED by `memo anatomy generate` from the Foundational Model of Anatomy (FMA) 5.1.0,
// University of Washington Structural Informatics Group, http://purl.org/sig/ont/fma.owl, CC BY 4.0, https://creativecommons.org/licenses/by/4.0/.
// Converted from OWL to SysML v2 by MEMO's anatomy extension. Do not edit: change the project's AnatomySelectors and regenerate.
package gastric_bypass_variants_anatomy_fma_core_postnatal_anatomical_structure {
    private import gastric_bypass_variants_anatomy_fma::*;

    part def <fma63863> AcellularAnatomicalStructure :> PostnatalAnatomicalStructure {
        doc /* Anatomical structure, each instance of which consists of some cell parts and cell substances and together does not constitute some cell or tissue. Examples: basement membrane, prostatic concretion. */
    }
    part def <fma63871> AcellularMembrane :> AcellularAnatomicalStructure;
    part def <fma63872> BasementMembrane :> AcellularMembrane;

    part def <fma67509> OrganSystemSubdivision :> PostnatalAnatomicalStructure {
        doc /* Anatomical structure, which consists of a specific set of the members of (predominantly) one organ or organ part subclass interconnected by zones of continuity or body substances; is demarcated from other subdivisions of the same organ system by one or more zones of continuity or anatomical lines; together with other subdivisions of the same organ system, it constitutes an organ system. Examples: rib cage, viscerocranium, integument, upper respiratory tract. */
    }

    part def <fma67135> PostnatalAnatomicalStructure :> AnatomicalStructure {
        doc /* Anatomical structure present after birth. */
    }
    part def <fma25569> SubdivisionOfAxialSkeletalSystem :> SubdivisionOfSkeletalSystem;
    part def <fma302079> SubdivisionOfPostcranialAxialSkeletalSystem :> SubdivisionOfAxialSkeletalSystem;

    part def <fma85544> SubdivisionOfSkeletalSystem :> OrganSystemSubdivision {
        doc /* Organ system subdivision which has as its direct parts a combination of any of the following structures: skeleton, skeletal membrane organs, skeletal ligaments, bursae, skeletal cartilage organs and portions of synovial fluid. */
    }
    part def <fma16201> SubdivisionOfVertebralColumn :> SubdivisionOfPostcranialAxialSkeletalSystem;
}
