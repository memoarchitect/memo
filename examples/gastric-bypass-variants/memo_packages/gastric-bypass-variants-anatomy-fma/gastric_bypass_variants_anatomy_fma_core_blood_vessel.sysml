// GENERATED by `memo anatomy generate` from the Foundational Model of Anatomy (FMA) 5.1.0,
// University of Washington Structural Informatics Group, http://purl.org/sig/ont/fma.owl, CC BY 4.0, https://creativecommons.org/licenses/by/4.0/.
// Converted from OWL to SysML v2 by MEMO's anatomy extension. Do not edit: change the project's AnatomySelectors and regenerate.
package gastric_bypass_variants_anatomy_fma_core_blood_vessel {
    private import gastric_bypass_variants_anatomy_fma::*;

    part def <fma63183> BloodVessel :> SegmentOfBloodVesselTreeOrgan {
        doc /* Segment of blood vessel tree organ which is a tubular structure the lumen of which contains blood; together with other spatially associated blood vessels constitute blood vessel tree organ. */
    }
    part def <fma13087> SegmentOfAorta :> SegmentOfArterialTrunk;
    part def <fma86256> SegmentOfArterialTrunk :> BloodVessel;
    part def <fma68045> SegmentOfThoracicAorta :> SegmentOfAorta;
}
