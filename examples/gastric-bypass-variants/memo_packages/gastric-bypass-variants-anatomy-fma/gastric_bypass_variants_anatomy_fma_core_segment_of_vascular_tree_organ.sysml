// GENERATED by `memo anatomy generate` from the Foundational Model of Anatomy (FMA) 5.1.0,
// University of Washington Structural Informatics Group, http://purl.org/sig/ont/fma.owl, CC BY 4.0, https://creativecommons.org/licenses/by/4.0/.
// Converted from OWL to SysML v2 by MEMO's anatomy extension. Do not edit: change the project's AnatomySelectors and regenerate.
package gastric_bypass_variants_anatomy_fma_core_segment_of_vascular_tree_organ {
    private import gastric_bypass_variants_anatomy_fma::*;
    part def <fma277359> AbdominalLymphaticChain :> LymphaticChain;
    part def <fma224641> AnteriorDeepCervicalLymphaticChain :> DeepCervicalLymphaticChain;
    part def <fma66146> BronchomediastinalLymphaticTree :> LymphaticTreeOrganPart;
    part def <fma223852> DeepCervicalLymphaticChain :> LymphaticChain;
    part def <fma234356> DiaphragmaticLymphaticChain :> LymphaticChain;

    part def <fma62865> LymphaticChain :> LymphaticTreeOrganPart {
        doc /* Segment of lymphatic tree organ which has as its direct parts one or more lymph nodes connected by two or more lymphatic vessels; together with other lymphatic chains forms a lymphatic tree organ part. */
    }

    part def <fma66132> LymphaticTreeOrganPart :> SegmentOfLymphaticTreeOrgan {
        doc /* Segment of lymphatic tree organ which has as its direct parts two or more lymphatic chains; together with other lymphatic organ part trees constitutes a lymphatic tree organ. Examples: subclavian lymphatic tree, right lumbar lymphatic tree. */
    }
    part def <fma224035> ParatrachealLymphaticChain :> LymphaticChain;
    part def <fma75623> PosteriorMediastinalLymphaticChain :> LymphaticChain;
    part def <fma224029> RetropharyngealLymphaticChain :> LymphaticChain;

    part def <fma86189> SegmentOfLymphaticTreeOrgan :> SegmentOfVascularTreeOrgan {
        doc /* Organ segment which is regional part of lymphatic tree organ. Examples: lymphatic chain, lymphatic plexus. */
    }
    part def <fma66156> SegmentOfThoracicDuct :> SegmentOfLymphaticTreeOrgan;
    part def <fma315270> SegmentOfThoracicPartOfThoracicDuct :> SegmentOfThoracicDuct;

    part def <fma50722> SegmentOfVascularTreeOrgan :> SegmentOfHollowTreeOrgan {
        doc /* Organ segment which is a regional part of a vascular tree organ. Examples: capillary, segment of arterial tree organ. */
    }
    part def <fma229531> SubdivisionOfLeftGastricLymphaticChain :> AbdominalLymphaticChain;
    part def <fma68028> T2PartOfThoracicDuct :> SegmentOfThoracicPartOfThoracicDuct;
    part def <fma68029> T3PartOfThoracicDuct :> SegmentOfThoracicPartOfThoracicDuct;
    part def <fma68030> T4PartOfThoracicDuct :> SegmentOfThoracicPartOfThoracicDuct;
    part def <fma68032> T6PartOfThoracicDuct :> SegmentOfThoracicPartOfThoracicDuct;
    part def <fma68033> T7PartOfThoracicDuct :> SegmentOfThoracicPartOfThoracicDuct;
    part def <fma68034> T8PartOfThoracicDuct :> SegmentOfThoracicPartOfThoracicDuct;
}
