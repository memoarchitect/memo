// GENERATED by `memo anatomy generate` from the Foundational Model of Anatomy (FMA) 5.1.0,
// University of Washington Structural Informatics Group, http://purl.org/sig/ont/fma.owl, CC BY 4.0, https://creativecommons.org/licenses/by/4.0/.
// Converted from OWL to SysML v2 by MEMO's anatomy extension. Do not edit: change the project's AnatomySelectors and regenerate.
package gastric_bypass_variants_anatomy_fma_cardiovascular_segment_of_blood_vessel_tree_organ {
    private import gastric_bypass_variants_anatomy_fma::*;
    part def <fma3789> AbdominalAorta :> SegmentOfAorta;
    part def <fma3768> ArchOfAorta :> SegmentOfThoracicAorta;
    part def <fma4149> EsophagealArtery :> SystemicArtery;
    part def <fma14862> EsophagealBranchOfLateralBranchOfLeftInferiorPhrenicArtery :> BranchOfInferiorPhrenicArtery;
    part def <fma14387> EsophagealTributaryOfAzygosVein :> TributaryOfAzygosVein;
    part def <fma62832> EsophagealTributaryOfBrachiocephalicVein :> EsophagealVein;
    part def <fma62833> EsophagealTributaryOfHemiAzygosVein :> EsophagealVein;
    part def <fma62834> EsophagealTributaryOfLeftGastricVein :> EsophagealVein;
    part def <fma4748> EsophagealVein :> SubdivisionOfBrachiocephalicVein;
    part def <fma14798> GastricBranchOfLeftGastroEpiploicArtery :> BranchOfLeftGastroEpiploicArtery;
    part def <fma75831> GastricBranchOfRightGastroEpiploicArtery :> BranchOfRightGastroEpiploicArtery;
    part def <fma14768> LeftGastricArtery :> BranchOfCeliacArtery;
    part def <fma15399> LeftGastricVein :> TributaryOfSuperiorMesentericVein;
    part def <fma15390> LeftGastroepiploicVein :> TributaryOfSplenicVein;
    part def <fma4694> LeftSubclavianArtery :> SubclavianArtery;
    part def <fma14795> PosteriorGastricArtery :> BranchOfSplenicArtery;
    part def <fma14776> RightGastricArtery :> BranchOfHepaticArteryProper;
    part def <fma15400> RightGastricVein :> TributaryOfSuperiorMesentericVein;
    part def <fma15397> RightGastroepiploicVein :> TributaryOfSuperiorMesentericVein;
    part def <fma14794> ShortGastricArtery :> BranchOfSplenicArtery;
    part def <fma15389> ShortGastricVein :> TributaryOfSplenicVein;
}
