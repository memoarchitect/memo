// GENERATED by `memo anatomy generate` from the Foundational Model of Anatomy (FMA) 5.1.0,
// University of Washington Structural Informatics Group, http://purl.org/sig/ont/fma.owl, CC BY 4.0, https://creativecommons.org/licenses/by/4.0/.
// Converted from OWL to SysML v2 by MEMO's anatomy extension. Do not edit: change the project's AnatomySelectors and regenerate.
package gastric_bypass_variants_anatomy_fma_cardiovascular_segment_of_hollow_tree_organ {
    private import gastric_bypass_variants_anatomy_fma::*;
    part def <fma229527> GastricLymphaticChain :> AbdominalLymphaticChain;
    part def <fma224309> HepaticLymphaticChain :> AbdominalLymphaticChain;
    part def <fma229536> InferiorPartOfLeftGastricLymphaticChain :> SubdivisionOfLeftGastricLymphaticChain;
    part def <fma66148> LeftBronchomediastinalLymphaticTree :> BronchomediastinalLymphaticTree;
    part def <fma224305> LeftGastricLymphaticChain :> AbdominalLymphaticChain;
    part def <fma224039> LeftParatrachealLymphaticChain :> ParatrachealLymphaticChain;
    part def <fma224033> LeftRetropharyngealLymphaticChain :> RetropharyngealLymphaticChain;
    part def <fma224311> PancreaticLymphaticChain :> AbdominalLymphaticChain;
    part def <fma229539> ParacardialPartOfLeftGastricLymphaticChain :> SubdivisionOfLeftGastricLymphaticChain;
    part def <fma229529> PyloricLymphaticChain :> AbdominalLymphaticChain;
    part def <fma224307> RightGastroEpiploicLymphaticChain :> AbdominalLymphaticChain;
    part def <fma224037> RightParatrachealLymphaticChain :> ParatrachealLymphaticChain;
    part def <fma224031> RightRetropharyngealLymphaticChain :> RetropharyngealLymphaticChain;
    part def <fma224296> SuperiorMesentericLymphaticChain :> AbdominalLymphaticChain;
    part def <fma229533> SuperiorPartOfLeftGastricLymphaticChain :> SubdivisionOfLeftGastricLymphaticChain;
}
