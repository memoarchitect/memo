// GENERATED by `memo anatomy generate` from the Foundational Model of Anatomy (FMA) 5.1.0,
// University of Washington Structural Informatics Group, http://purl.org/sig/ont/fma.owl, CC BY 4.0, https://creativecommons.org/licenses/by/4.0/.
// Converted from OWL to SysML v2 by MEMO's anatomy extension. Do not edit: change the project's AnatomySelectors and regenerate.
package gastric_bypass_variants_anatomy_fma_core_arborial_segment_of_arterial_tree_organ {
    private import gastric_bypass_variants_anatomy_fma::*;
    part def <fma86187> ArborialSegmentOfArterialTreeOrgan :> SegmentOfBloodVesselTreeOrgan;
    part def <fma50720> Artery :> ArborialSegmentOfArterialTreeOrgan;
    part def <fma70429> BranchOfCeliacArtery :> SystemicArtery;
    part def <fma70433> BranchOfCommonHepaticArtery :> BranchOfCeliacArtery;
    part def <fma70436> BranchOfGastroduodenalArtery :> BranchOfCommonHepaticArtery;
    part def <fma14837> BranchOfHepaticArteryProper :> BranchOfCommonHepaticArtery;
    part def <fma14854> BranchOfInferiorPhrenicArtery :> SystemicArtery;
    part def <fma31951> BranchOfLeftBronchialArtery :> BronchialArtery;
    part def <fma21533> BranchOfLeftGastroEpiploicArtery :> BranchOfSplenicArtery;
    part def <fma31937> BranchOfRightBronchialArtery :> BronchialArtery;
    part def <fma21525> BranchOfRightGastroEpiploicArtery :> BranchOfGastroduodenalArtery;
    part def <fma70470> BranchOfSplenicArtery :> BranchOfCeliacArtery;
    part def <fma68109> BronchialArtery :> SystemicArtery;
    part def <fma62824> EsophagealBranchOfLeftBronchialArtery :> BranchOfLeftBronchialArtery;
    part def <fma62825> EsophagealBranchOfLeftFirstBronchialArtery :> EsophagealBranchOfLeftBronchialArtery;
    part def <fma62826> EsophagealBranchOfLeftSecondBronchialArtery :> EsophagealBranchOfLeftBronchialArtery;
    part def <fma62823> EsophagealBranchOfRightBronchialArtery :> BranchOfRightBronchialArtery;

    part def <fma66464> SystemicArtery :> Artery {
        doc /* Arterial tree, each instance of which carries oxygenated blood from some heart. */
    }
}
