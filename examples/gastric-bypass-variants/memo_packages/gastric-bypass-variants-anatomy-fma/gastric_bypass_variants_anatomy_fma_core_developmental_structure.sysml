// GENERATED by `memo anatomy generate` from the Foundational Model of Anatomy (FMA) 5.1.0,
// University of Washington Structural Informatics Group, http://purl.org/sig/ont/fma.owl, CC BY 4.0, https://creativecommons.org/licenses/by/4.0/.
// Converted from OWL to SysML v2 by MEMO's anatomy extension. Do not edit: change the project's AnatomySelectors and regenerate.
package gastric_bypass_variants_anatomy_fma_core_developmental_structure {
    private import gastric_bypass_variants_anatomy_fma::*;
    part def <fma292328> DevelopmentalCardinalOrganPart :> DevelopmentalStructure;

    part def <fma292313> DevelopmentalStructure :> AnatomicalStructure {
        doc /* Anatomical structure present before birth. */
    }
    part def <fma295632> EmbryonicOrganPart :> DevelopmentalCardinalOrganPart;
    part def <fma45616> Foregut :> RegionOfEmbryonicGut;
    part def <fma45617> Midgut :> RegionOfEmbryonicGut;
    part def <fma295610> RegionOfEmbryonicGut :> EmbryonicOrganPart;
}
