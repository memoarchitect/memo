// GENERATED by `memo anatomy generate` from the Foundational Model of Anatomy (FMA) 5.1.0,
// University of Washington Structural Informatics Group, http://purl.org/sig/ont/fma.owl, CC BY 4.0, https://creativecommons.org/licenses/by/4.0/.
// Converted from OWL to SysML v2 by MEMO's anatomy extension. Do not edit: change the project's AnatomySelectors and regenerate.
package gastric_bypass_variants_anatomy_fma_core_cardinal_tissue_part {
    private import gastric_bypass_variants_anatomy_fma::*;

    part def <fma67536> CardinalTissuePart :> PostnatalAnatomicalStructure {
        doc /* Anatomical structure, each instance of which is a subdivision of some tissue demarcated by bonafide or fiat boundaries. Examples: stratum germinativum, lamina of cerebral cortex. */
    }
    part def <fma63621> CryptOfLieberkuhn :> SimpleTubularGland;
    part def <fma86453> LayerOfEpitheliumOfEsophagus :> TissueComponentOfEpithelium;
    part def <fma62883> SimpleBranchedTubularGland :> SimpleExocrineGland;
    part def <fma62083> SimpleExocrineGland :> CardinalTissuePart;
    part def <fma62881> SimpleTubularGland :> SimpleExocrineGland;
    part def <fma67538> TissueComponentOfEpithelium :> CardinalTissuePart;
}
