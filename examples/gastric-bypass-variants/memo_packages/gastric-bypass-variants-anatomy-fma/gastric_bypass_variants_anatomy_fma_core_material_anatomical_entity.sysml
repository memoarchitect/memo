// GENERATED by `memo anatomy generate` from the Foundational Model of Anatomy (FMA) 5.1.0,
// University of Washington Structural Informatics Group, http://purl.org/sig/ont/fma.owl, CC BY 4.0, https://creativecommons.org/licenses/by/4.0/.
// Converted from OWL to SysML v2 by MEMO's anatomy extension. Do not edit: change the project's AnatomySelectors and regenerate.
package gastric_bypass_variants_anatomy_fma_core_material_anatomical_entity {
    private import gastric_bypass_variants_anatomy_fma::*;

    part def <fma67165> MaterialAnatomicalEntity :> PhysicalAnatomicalEntity {
        doc /* Physical anatomical entity, each instance of which has mass. Examples: hemoglobin molecule, mitochondrion, hepatocyte, erythrocyte, heart, head, blood, urine. */
    }

    part def <fma280556> PortionOfBodyFluid :> PortionOfBodySubstance {
        doc /* Portion of body substance which has as its parts of a mixture of fluid, solutes and particles. */
    }

    part def <fma280564> PortionOfBodyFluidSuspension :> PortionOfBodyFluid {
        doc /* Portion of body fluid which has as its parts portion of body fluid solution and particles. */
    }

    part def <fma9669> PortionOfBodySubstance :> MaterialAnatomicalEntity {
        doc /* Material anatomical entity, each instance of which is either in fluid or solid state, with or without admixture of some cells and biological macromolecules; produced by some anatomical structures or derived from some inhaled or ingested substances that have been modified by anatomical structures. Examples: portion of saliva, portion of semen, portion of cerebrospinal fluid, portion of respiratory air, portion of urine, feces, portion of blood, portion of plasma, portion of lymph. */
    }
    part def <fma280560> PortionOfColloidalBodySubstance :> PortionOfBodyFluidSuspension;

    part def <fma9672> PortionOfExtracellularMatrix :> PortionOfColloidalBodySubstance {
        doc /* Body substance which has as its parts ground substance and connective tissue fibers. */
    }
}
