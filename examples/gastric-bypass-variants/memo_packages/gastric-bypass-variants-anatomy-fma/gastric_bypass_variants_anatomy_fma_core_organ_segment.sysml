// GENERATED by `memo anatomy generate` from the Foundational Model of Anatomy (FMA) 5.1.0,
// University of Washington Structural Informatics Group, http://purl.org/sig/ont/fma.owl, CC BY 4.0, https://creativecommons.org/licenses/by/4.0/.
// Converted from OWL to SysML v2 by MEMO's anatomy extension. Do not edit: change the project's AnatomySelectors and regenerate.
package gastric_bypass_variants_anatomy_fma_core_organ_segment {
    private import gastric_bypass_variants_anatomy_fma::*;
    part def <fma9706> BileDuct :> Duct;
    part def <fma27443> C6SegmentOfAnteriorLongitudinalLigament :> CervicalVertebralSegmentOfAnteriorLongitudinalLigament;
    part def <fma27445> C7SegmentOfAnteriorLongitudinalLigament :> CervicalVertebralSegmentOfAnteriorLongitudinalLigament;
    part def <fma25021> CervicalVertebralSegmentOfAnteriorLongitudinalLigament :> SegmentOfAnteriorLongitudinalLigament;

    part def <fma30320> Duct :> OrganSegment {
        doc /* Organ segment which consists of a wall lined with epithelial cells and which encloses a lumen. */
    }
    part def <fma14678> ExtrahepaticBileDuct :> BileDuct;

    part def <fma86140> OrganSegment :> OrganRegion {
        doc /* Organ region, each instance of which has one or more anchored fiat boundaries. Examples: artery, cervical part of esophagus, pelvic part of vagina, horn of thyroid cartilage, anterior segment of eyeball. */
    }
    part def <fma63978> SegmentOfAnteriorLongitudinalLigament :> OrganSegment;
    part def <fma222905> SegmentOfColon :> SegmentOfLargeIntestine;
    part def <fma71893> SegmentOfCommonBileDuct :> ExtrahepaticBileDuct;

    part def <fma222904> SegmentOfDuodenum :> OrganSegment {
        doc /* Organ segment which is regional part of duodenum. Examples: superior part of duodenum, duodenal bulb. */
    }

    part def <fma55269> SegmentOfEsophagus :> OrganSegment {
        doc /* Organ segment which is regional part of esophagus. Examples: cervical part of esophagus, vertebral segment of esophagus. */
    }

    part def <fma14540> SegmentOfLargeIntestine :> OrganSegment {
        doc /* Organ segment which is regional part of large intestine. Examples: colon, rectum, ileocecal lip. */
    }
    part def <fma14092> SegmentOfSmallIntestine :> OrganSegment;

    part def <fma26659> SegmentOfTrachea :> OrganSegment {
        doc /* Organ segment which is regional part of trachea. Examples: cervical segment of trachea, bifurcation of trachea. */
    }
    part def <fma255838> SubdivisionOfVertebralSegmentOfEsophagus :> SegmentOfEsophagus;
    part def <fma27450> T2SegmentOfAnteriorLongitudinalLigament :> ThoracicVertebralSegmentOfAnteriorLongitudinalLigament;
    part def <fma27453> T3SegmentOfAnteriorLongitudinalLigament :> ThoracicVertebralSegmentOfAnteriorLongitudinalLigament;
    part def <fma27455> T4SegmentOfAnteriorLongitudinalLigament :> ThoracicVertebralSegmentOfAnteriorLongitudinalLigament;
    part def <fma16074> ThoracicVertebralSegmentOfAnteriorLongitudinalLigament :> SegmentOfAnteriorLongitudinalLigament;
    part def <fma52525> VertebralSegmentOfEsophagus :> SegmentOfEsophagus;
    part def <fma86173> VertebralSegmentOfTrachea :> SegmentOfTrachea;
}
