// GENERATED by `memo anatomy generate` from the Foundational Model of Anatomy (FMA) 5.1.0,
// University of Washington Structural Informatics Group, http://purl.org/sig/ont/fma.owl, CC BY 4.0, https://creativecommons.org/licenses/by/4.0/.
// Converted from OWL to SysML v2 by MEMO's anatomy extension. Do not edit: change the project's AnatomySelectors and regenerate.
package gastric_bypass_variants_anatomy_fma_core_organ_component {
    private import gastric_bypass_variants_anatomy_fma::*;
    part def <fma9404> EsophagealGland :> OrganComponentGland;
    part def <fma14919> GastricGland :> OrganComponentGland;
    part def <fma297481> MuscleFiberGroup :> OrganComponent;
    part def <fma85353> MuscleLayerOfDigestiveTract :> SmoothMuscleLayer;

    part def <fma14065> OrganComponent :> CardinalOrganPart {
        doc /* Cardinal organ part, each instance of which is bounded predominantly by some bonafide boundaries. Examples: lobe of lung, osteon, acinus, submucosa, anterior leaflet of mitral valve, fibrous capsule of kidney, compact bone, striated muscle fasciculus. */
    }
    part def <fma7146> OrganComponentGland :> OrganComponent;

    part def <fma297487> SmoothMuscleFiberGroup :> MuscleFiberGroup {
        doc /* Muscle fiber group which consists of non-striated muscle fibers invested by connective tissue fibers. */
    }

    part def <fma297484> SmoothMuscleLayer :> SmoothMuscleFiberGroup {
        doc /* Smooth muscle fiber group arranged in sheets. */
    }

    part def <fma82482> WallOfOrgan :> OrganComponent {
        doc /* Organ component adjacent to an organ cavity and which consists of a maximal aggregate of organ component layers. */
    }
}
