// GENERATED by `memo anatomy generate` from the Foundational Model of Anatomy (FMA) 5.1.0,
// University of Washington Structural Informatics Group, http://purl.org/sig/ont/fma.owl, CC BY 4.0, https://creativecommons.org/licenses/by/4.0/.
// Converted from OWL to SysML v2 by MEMO's anatomy extension. Do not edit: change the project's AnatomySelectors and regenerate.
package gastric_bypass_variants_anatomy_fma_core_organ_zone {
    private import gastric_bypass_variants_anatomy_fma::*;
    part def <fma9141> BodyOfThoracicVertebra :> BodyOfVertebra;
    part def <fma11945> BodyOfVertebra :> ZoneOfVertebra;
    part def <fma322326> CrusOfLumbarPartOfDiaphragm :> ZoneOfDiaphragm;
    part def <fma0327495> FlexureOfDuodenum :> ZoneOfDuodenum;

    part def <fma55268> OrganZone :> OrganRegion {
        doc /* Organ region, each instance of which has one or more floating fiat boundaries. Examples: apical zone of lung, superior pole of kidney, gingiva, apex of prostate, ascending colon proper. */
    }
    part def <fma322099> PyloricPartOfStomach :> ZoneOfStomach;
    part def <fma68038> SubzoneOfAzygosVein :> ZoneOfTrunkOfAzygosVein;
    part def <fma71084> T4PartOfAzygosVein :> SubzoneOfAzygosVein;
    part def <fma68039> T5PartOfAzygosVein :> SubzoneOfAzygosVein;
    part def <fma68040> T6PartOfAzygosVein :> SubzoneOfAzygosVein;
    part def <fma68041> T7PartOfAzygosVein :> SubzoneOfAzygosVein;
    part def <fma68042> T8PartOfAzygosVein :> SubzoneOfAzygosVein;
    part def <fma10483> ZoneOfBoneOrgan :> OrganZone;
    part def <fma58275> ZoneOfDiaphragm :> ZoneOfMuscleOrgan;
    part def <fma14925> ZoneOfDuodenum :> ZoneOfSmallIntestine;
    part def <fma71048> ZoneOfFibrousPericardium :> OrganZone;
    part def <fma16980> ZoneOfJejunum :> ZoneOfSmallIntestine;
    part def <fma46279> ZoneOfLongusColli :> ZoneOfMuscleOrgan;
    part def <fma10474> ZoneOfMuscleOrgan :> OrganZone;
    part def <fma323907> ZoneOfSmallIntestine :> OrganZone;
    part def <fma14558> ZoneOfStomach :> OrganZone;
    part def <fma67316> ZoneOfTrunkOfAzygosVein :> ZoneOfTrunkOfVein;
    part def <fma0327646> ZoneOfTrunkOfVein :> ZoneOfVein;
    part def <fma67319> ZoneOfVein :> OrganZone;
    part def <fma85304> ZoneOfVertebra :> ZoneOfBoneOrgan;
}
