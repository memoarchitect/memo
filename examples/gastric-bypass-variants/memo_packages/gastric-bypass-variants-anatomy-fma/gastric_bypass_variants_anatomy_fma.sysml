// GENERATED by `memo anatomy generate` from the Foundational Model of Anatomy (FMA) 5.1.0,
// University of Washington Structural Informatics Group, http://purl.org/sig/ont/fma.owl, CC BY 4.0, https://creativecommons.org/licenses/by/4.0/.
// Converted from OWL to SysML v2 by MEMO's anatomy extension. Do not edit: change the project's AnatomySelectors and regenerate.
//
// Selected by:
//   memo_examples_gastric_bypass_variants_project::upperGi: fma7131, fma7148, fma7206, fma7207 (part depth 3)
package gastric_bypass_variants_anatomy_fma {
    public import gastric_bypass_variants_anatomy_fma_alimentary::*;
    public import gastric_bypass_variants_anatomy_fma_body_proper::*;
    public import gastric_bypass_variants_anatomy_fma_cardiovascular_material_anatomical_entity::*;
    public import gastric_bypass_variants_anatomy_fma_cardiovascular_segment_of_blood_vessel_tree_organ::*;
    public import gastric_bypass_variants_anatomy_fma_cardiovascular_segment_of_hollow_tree_organ::*;
    public import gastric_bypass_variants_anatomy_fma_core::*;
    public import gastric_bypass_variants_anatomy_fma_core_anatomical_boundary_entity::*;
    public import gastric_bypass_variants_anatomy_fma_core_anatomical_cluster::*;
    public import gastric_bypass_variants_anatomy_fma_core_anatomical_set::*;
    public import gastric_bypass_variants_anatomy_fma_core_anatomical_space::*;
    public import gastric_bypass_variants_anatomy_fma_core_anatomical_structure::*;
    public import gastric_bypass_variants_anatomy_fma_core_anatomical_surface::*;
    public import gastric_bypass_variants_anatomy_fma_core_arborial_segment_of_arterial_tree_organ::*;
    public import gastric_bypass_variants_anatomy_fma_core_arborial_segment_of_venous_tree_organ::*;
    public import gastric_bypass_variants_anatomy_fma_core_blood_vessel::*;
    public import gastric_bypass_variants_anatomy_fma_core_bona_fide_anatomical_surface::*;
    public import gastric_bypass_variants_anatomy_fma_core_cardinal_organ_part::*;
    public import gastric_bypass_variants_anatomy_fma_core_cardinal_tissue_part::*;
    public import gastric_bypass_variants_anatomy_fma_core_cell_part_cluster::*;
    public import gastric_bypass_variants_anatomy_fma_core_developmental_structure::*;
    public import gastric_bypass_variants_anatomy_fma_core_immaterial_anatomical_entity::*;
    public import gastric_bypass_variants_anatomy_fma_core_material_anatomical_entity::*;
    public import gastric_bypass_variants_anatomy_fma_core_nerve::*;
    public import gastric_bypass_variants_anatomy_fma_core_organ::*;
    public import gastric_bypass_variants_anatomy_fma_core_organ_component::*;
    public import gastric_bypass_variants_anatomy_fma_core_organ_component_layer::*;
    public import gastric_bypass_variants_anatomy_fma_core_organ_component_of_lymphatic_tree_organ::*;
    public import gastric_bypass_variants_anatomy_fma_core_organ_region::*;
    public import gastric_bypass_variants_anatomy_fma_core_organ_segment::*;
    public import gastric_bypass_variants_anatomy_fma_core_organ_zone::*;
    public import gastric_bypass_variants_anatomy_fma_core_physical_anatomical_entity::*;
    public import gastric_bypass_variants_anatomy_fma_core_portion_of_tissue::*;
    public import gastric_bypass_variants_anatomy_fma_core_postnatal_anatomical_structure::*;
    public import gastric_bypass_variants_anatomy_fma_core_region_of_organ_component::*;
    public import gastric_bypass_variants_anatomy_fma_core_region_of_surface_of_organ::*;
    public import gastric_bypass_variants_anatomy_fma_core_segment_of_blood_vessel_tree_organ::*;
    public import gastric_bypass_variants_anatomy_fma_core_segment_of_hollow_tree_organ::*;
    public import gastric_bypass_variants_anatomy_fma_core_segment_of_neural_tree_organ::*;
    public import gastric_bypass_variants_anatomy_fma_core_segment_of_vascular_tree_organ::*;
    public import gastric_bypass_variants_anatomy_fma_core_surface_of_organ_region::*;
    public import gastric_bypass_variants_anatomy_fma_fascial::*;
    public import gastric_bypass_variants_anatomy_fma_musculoskeletal_anatomical_structure::*;
    public import gastric_bypass_variants_anatomy_fma_musculoskeletal_cardinal_organ_part::*;
    public import gastric_bypass_variants_anatomy_fma_musculoskeletal_organ::*;
    public import gastric_bypass_variants_anatomy_fma_nervous_anatomical_cluster::*;
    public import gastric_bypass_variants_anatomy_fma_nervous_nerve::*;
    public import gastric_bypass_variants_anatomy_fma_nervous_postnatal_anatomical_structure::*;
    public import gastric_bypass_variants_anatomy_fma_respiratory::*;
}
