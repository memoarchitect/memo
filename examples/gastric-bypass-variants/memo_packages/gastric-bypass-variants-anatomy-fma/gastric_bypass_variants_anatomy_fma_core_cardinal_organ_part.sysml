// GENERATED by `memo anatomy generate` from the Foundational Model of Anatomy (FMA) 5.1.0,
// University of Washington Structural Informatics Group, http://purl.org/sig/ont/fma.owl, CC BY 4.0, https://creativecommons.org/licenses/by/4.0/.
// Converted from OWL to SysML v2 by MEMO's anatomy extension. Do not edit: change the project's AnatomySelectors and regenerate.
package gastric_bypass_variants_anatomy_fma_core_cardinal_organ_part {
    private import gastric_bypass_variants_anatomy_fma::*;

    part def <fma82472> CardinalOrganPart :> PostnatalAnatomicalStructure {
        doc /* Anatomical structure, each instance of which has as its direct parts some instance of portions of two or more types of tissue and is continuous with some instance of one or more anatomical structures, likewise constituted by some portions of two or more tissues distinct from those of their complement. */
    }
}
