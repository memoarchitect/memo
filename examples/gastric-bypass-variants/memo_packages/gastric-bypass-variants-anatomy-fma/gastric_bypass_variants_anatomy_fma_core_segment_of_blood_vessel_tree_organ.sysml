// GENERATED by `memo anatomy generate` from the Foundational Model of Anatomy (FMA) 5.1.0,
// University of Washington Structural Informatics Group, http://purl.org/sig/ont/fma.owl, CC BY 4.0, https://creativecommons.org/licenses/by/4.0/.
// Converted from OWL to SysML v2 by MEMO's anatomy extension. Do not edit: change the project's AnatomySelectors and regenerate.
package gastric_bypass_variants_anatomy_fma_core_segment_of_blood_vessel_tree_organ {
    private import gastric_bypass_variants_anatomy_fma::*;

    part def <fma312599> SegmentOfBloodVesselTreeOrgan :> SegmentOfVascularTreeOrgan {
        doc /* Organ segment which is regional part of blood vessel tree organ. Examples: artery, vein, blood vessel. */
    }
}
