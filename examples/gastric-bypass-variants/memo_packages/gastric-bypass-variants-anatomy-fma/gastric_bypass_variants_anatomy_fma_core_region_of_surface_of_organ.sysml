// GENERATED by `memo anatomy generate` from the Foundational Model of Anatomy (FMA) 5.1.0,
// University of Washington Structural Informatics Group, http://purl.org/sig/ont/fma.owl, CC BY 4.0, https://creativecommons.org/licenses/by/4.0/.
// Converted from OWL to SysML v2 by MEMO's anatomy extension. Do not edit: change the project's AnatomySelectors and regenerate.
package gastric_bypass_variants_anatomy_fma_core_region_of_surface_of_organ {
    private import gastric_bypass_variants_anatomy_fma::*;
    part def <fma17042> ExternalSurfaceOfEsophagus :> RegionOfSurfaceOfEsophagus;
    part def <fma17043> InternalSurfaceOfEsophagus :> RegionOfSurfaceOfEsophagus;
    part def <fma322101> RegionOfSurfaceOfEsophagus :> RegionOfSurfaceOfOrgan;

    part def <fma24210> RegionOfSurfaceOfOrgan :> BonaFideAnatomicalSurface {
        doc /* Anatomical surface, which is the subdivision of the surface of an organ. Examples: diaphragmatic surface of lung, sternocostal surface of heart, anterior surface of stomach. */
    }
}
