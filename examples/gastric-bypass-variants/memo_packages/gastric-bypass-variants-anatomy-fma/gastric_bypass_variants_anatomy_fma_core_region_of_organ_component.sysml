// GENERATED by `memo anatomy generate` from the Foundational Model of Anatomy (FMA) 5.1.0,
// University of Washington Structural Informatics Group, http://purl.org/sig/ont/fma.owl, CC BY 4.0, https://creativecommons.org/licenses/by/4.0/.
// Converted from OWL to SysML v2 by MEMO's anatomy extension. Do not edit: change the project's AnatomySelectors and regenerate.
package gastric_bypass_variants_anatomy_fma_core_region_of_organ_component {
    private import gastric_bypass_variants_anatomy_fma::*;
    part def <fma17397> AnteriorWallOfZoneOfStomach :> RegionOfWallOfStomach;
    part def <fma15953> DuodenalPapilla :> SurfacePapilla;
    part def <fma85385> MucosaOfRegionOfJejunum :> MucosaOfZoneOfSmallIntestine;
    part def <fma63007> MucosaOfSegmentOfEsophagus :> RegionOfMucosa;
    part def <fma85384> MucosaOfZoneOfDuodenum :> MucosaOfZoneOfSmallIntestine;
    part def <fma85383> MucosaOfZoneOfSmallIntestine :> RegionOfMucosa;
    part def <fma17052> MucosaOfZoneOfStomach :> RegionOfMucosa;
    part def <fma63039> MuscleLayerOfSegmentOfEsophagus :> RegionOfMuscleLayerOfOrgan;
    part def <fma17111> MuscleLayerOfSubdivisionOfDuodenum :> MuscleLayerOfZoneOfSmallIntestine;
    part def <fma17137> MuscleLayerOfSubdivisionOfJejunum :> MuscleLayerOfZoneOfSmallIntestine;
    part def <fma83561> MuscleLayerOfZoneOfSmallIntestine :> RegionOfMuscleLayerOfOrgan;
    part def <fma17062> MuscleLayerOfZoneOfStomach :> RegionOfMuscleLayerOfOrgan;
    part def <fma17406> PosteriorWallOfZoneOfStomach :> RegionOfWallOfStomach;
    part def <fma27423> RegionOfBronchus :> RegionOfOrganComponent;
    part def <fma85358> RegionOfMucosa :> RegionOfOrganComponent;
    part def <fma85354> RegionOfMuscleLayerOfOrgan :> RegionOfOrganComponent;

    part def <fma86103> RegionOfOrganComponent :> CardinalOrganPart {
        doc /* Cardinal organ part. each instance of which is a fiat subdivision of some organ component. Examples: wall of cervical part of esophagus, mucosa of body of stomach. */
    }
    part def <fma21453> RegionOfParietalPleura :> RegionOfPleura;
    part def <fma64794> RegionOfPleura :> RegionOfSerousMembrane;
    part def <fma64796> RegionOfSerousMembrane :> RegionOfOrganComponent;
    part def <fma85392> RegionOfSubmucosa :> RegionOfOrganComponent;
    part def <fma86109> RegionOfWallOfDuodenum_fma86109 :> RegionOfWallOfSmallIntestine;
    part def <fma86105> RegionOfWallOfEsophagus :> RegionOfOrganComponent;
    part def <fma86110> RegionOfWallOfJejunum :> RegionOfWallOfSmallIntestine;
    part def <fma86108> RegionOfWallOfSmallIntestine :> RegionOfOrganComponent;
    part def <fma86116> RegionOfWallOfStomach :> RegionOfOrganComponent;
    part def <fma85424> SerosaOfOrganRegion :> RegionOfOrganComponent;
    part def <fma85425> SerosaOfZoneOfDuodenum :> SerosaOfZoneOfSmallIntestine;
    part def <fma85426> SerosaOfZoneOfJejunum :> SerosaOfZoneOfSmallIntestine;
    part def <fma20638> SerosaOfZoneOfSmallIntestine :> SerosaOfOrganRegion;
    part def <fma17072> SerosaOfZoneOfStomach :> SerosaOfOrganRegion;
    part def <fma85396> SubmucosaOfRegionOfJejunum :> SubmucosaOfZoneOfSmallIntestine;
    part def <fma63035> SubmucosaOfSegmentOfEsophagus :> RegionOfSubmucosa;
    part def <fma85395> SubmucosaOfZoneOfDuodenum :> SubmucosaOfZoneOfSmallIntestine;
    part def <fma85394> SubmucosaOfZoneOfSmallIntestine :> RegionOfSubmucosa;
    part def <fma17057> SubmucosaOfZoneOfStomach :> RegionOfSubmucosa;
    part def <fma85413> SubserosaOfOrganRegion :> RegionOfOrganComponent;
    part def <fma85415> SubserosaOfZoneOfDuodenum :> SubserosaOfZoneOfSmallIntestine;
    part def <fma85416> SubserosaOfZoneOfJejunum :> SubserosaOfZoneOfSmallIntestine;
    part def <fma85414> SubserosaOfZoneOfSmallIntestine :> SubserosaOfOrganRegion;
    part def <fma17067> SubserosaOfZoneOfStomach :> SubserosaOfOrganRegion;
    part def <fma82504> SurfacePapilla :> RegionOfOrganComponent;
    part def <fma71077> T5PartOfLeftMainBronchus :> T5RegionOfMainBronchus;
    part def <fma71080> T5PartOfRightMainBronchus :> T5RegionOfMainBronchus;
    part def <fma86170> T5RegionOfMainBronchus :> VerterbalRegionOfMainBronchus;
    part def <fma71073> VerterbalRegionOfMainBronchus :> RegionOfBronchus;
}
