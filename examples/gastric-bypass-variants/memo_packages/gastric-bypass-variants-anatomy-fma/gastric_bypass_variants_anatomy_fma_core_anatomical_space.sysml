// GENERATED by `memo anatomy generate` from the Foundational Model of Anatomy (FMA) 5.1.0,
// University of Washington Structural Informatics Group, http://purl.org/sig/ont/fma.owl, CC BY 4.0, https://creativecommons.org/licenses/by/4.0/.
// Converted from OWL to SysML v2 by MEMO's anatomy extension. Do not edit: change the project's AnatomySelectors and regenerate.
package gastric_bypass_variants_anatomy_fma_core_anatomical_space {
    private import gastric_bypass_variants_anatomy_fma::*;

    part def <fma67552> AnatomicalCavity :> AnatomicalSpace {
        doc /* Anatomical space which contains portions of one or more body substances and is bounded by the internal surface of one maximally connected anatomical structure or two or more adjacent anatomical structures. Examples: nasal cavity, cavity of stomach, pharyngeal recess space, lumen of artery, cavity of serous sac. */
    }

    part def <fma84926> AnatomicalCompartmentSpace :> AnatomicalSpace {
        doc /* Anatomical space which contains two or more anatomical structures demarcated by bona fide boundaries and is bounded by the surface of one or more anatomical structures. Examples: orbital cavity, suprasternal space, thoracic cavity, fascial space, hepatic lacuna. */
    }

    part def <fma9338> AnatomicalConduitSpace :> AnatomicalSpace {
        doc /* Anatomical space which connects two or more compartment spaces or two or more anatomical cavities. Examples: foramen magnum, pyloric orifice, space of right inguinal canal, nutrient canal space, */
    }

    part def <fma3724> AnatomicalOrifice :> AnatomicalConduitSpace {
        doc /* Anatomical conduit space that connects two adjacent body spaces, surrounded by two or more subdivisions of two or more organs or organ parts. Examples: right atrioventricular orifice, orifice of artery, hilum of kidney, porta hepatis. */
    }

    part def <fma5897> AnatomicalSpace :> ImmaterialAnatomicalEntity {
        doc /* Immaterial anatomical entity, each instance of which has three spatial dimensions. Examples: body cavity, thoracic cavity, lesser sac, cavity of right atrium, lumen of aorta, mediastinal space, space of anterior compartment of forearm. */
    }
    part def <fma85007> BodyCavitySubdivision :> SpaceOfCompartmentOfTrunk;

    part def <fma24034> CavityOfOrganPart :> AnatomicalCavity {
        doc /* Anatomical cavity, which is surrounded by an organ part; is separated from the cavity or lumen of other organ parts of the same organ by anatomical structures. Examples: cavity of right atrium, medullary cavity of long bone, bone marrow cavity. */
    }

    part def <fma9336> CavityOfSubdivisionOfSerousSac :> OrganCavitySubdivision {
        doc /* Organ cavity subdivision that is a part of a serous cavity, demarcated from other serous cavity subdivisions by one or more anatomical structures or anatomical surfaces; together with other serous cavity subdivisions, it constitutes the serous cavity. Examples: costodiaphragmatic recess, oblique sinus of pericardial cavity, lesser sac, suprapatellar bursal space. */
    }
    part def <fma20683> LeftPosteriorSubphrenicSpace :> SubdivisionOfSubphrenicSpace;
    part def <fma18478> LumenOfSegmentOfDuodenum :> OrganCavitySubdivision;
    part def <fma18482> LumenOfSegmentOfEsophagus :> OrganCavitySubdivision;
    part def <fma17228> LumenOfSmallIntestinalGland :> SubdivisionOfLumenOfSmallIntestine;
    part def <fma18479> LumenOfZoneOfJejunum :> OrganCavitySubdivision;
    part def <fma18481> LumenOfZoneOfStomach :> CavityOfOrganPart;

    part def <fma12237> OrganCavity :> AnatomicalCavity {
        doc /* Anatomical cavity, which is surrounded by all morphological parts of an organ; is continuous within the organ; contains one or more body substances. Examples: pericardial cavity, cavity of stomach, cavity of uterus. */
    }

    part def <fma9337> OrganCavitySubdivision :> AnatomicalCavity {
        doc /* Anatomical cavity, which is surrounded by a morphological subdivision of an organ; is continuous with other organ cavity subdivisions of the same organ; together with other organ cavity subdivisions, it constitutes the organ cavity. Examples: lumen of pyloric antrum, lumen of bronchus, cavity of alveolar sac. */
    }
    part def <fma14563> OrificeOfStomach :> AnatomicalOrifice;
    part def <fma84955> SpaceOfAnteriorCompartmentOfNeck :> SpaceOfCompartmentOfNeck;
    part def <fma84954> SpaceOfCompartmentOfNeck :> AnatomicalCompartmentSpace;
    part def <fma85005> SpaceOfCompartmentOfTrunk :> AnatomicalCompartmentSpace;
    part def <fma20679> SubdivisionOfCavityOfGreaterSac :> SubdivisionOfPeritonealCavity;
    part def <fma62951> SubdivisionOfLumenOfSmallIntestine :> OrganCavitySubdivision;
    part def <fma85019> SubdivisionOfMediastinalSpace :> SubdivisionOfThoracicCavity;
    part def <fma14706> SubdivisionOfPeritonealCavity :> CavityOfSubdivisionOfSerousSac;
    part def <fma81141> SubdivisionOfSubphrenicSpace :> SubdivisionOfSupracolicSpace;
    part def <fma20681> SubdivisionOfSupracolicSpace :> SubdivisionOfCavityOfGreaterSac;
    part def <fma79192> SubdivisionOfThoracicCavity :> BodyCavitySubdivision;
}
