// GENERATED by `memo anatomy generate` from the Foundational Model of Anatomy (FMA) 5.1.0,
// University of Washington Structural Informatics Group, http://purl.org/sig/ont/fma.owl, CC BY 4.0, https://creativecommons.org/licenses/by/4.0/.
// Converted from OWL to SysML v2 by MEMO's anatomy extension. Do not edit: change the project's AnatomySelectors and regenerate.
package gastric_bypass_variants_anatomy_fma_core_portion_of_tissue {
    private import gastric_bypass_variants_anatomy_fma::*;

    part def <fma63897> AreolarConnectiveTissue :> LooseConnectiveTissue {
        doc /* Loose connective tissue located at the outer and inner layers of organs. Examples: submucosal connective tissue, tunica adventitia of artery, papillary dermis, superficial fascia of dorsum of hand. */
    }
    part def <fma263484> ConnectiveTissueOfRegionOfVisceralPeritoneum :> ConnectiveTissueOfSerousMembrane;
    part def <fma64786> ConnectiveTissueOfSerousMembrane :> DenseIrregularConnectiveTissue;

    part def <fma20109> DenseIrregularConnectiveTissue :> IrregularConnectiveTissue {
        doc /* Irregular connective tissue is an irregular connective tissue, the intercellular matrix of which contains a dense irregular network of collagen and elastic fiber bundles. Examples: connective tissue of peritoneum, connective tissue of fibrous pericardium. */
    }

    part def <fma64781> DenseRegularCollagenousTissue :> RegularConnectiveTissue {
        doc /* Regular connective tissue, the intercellular matrix of which consists predominantly of collagen fiber bundles arranged in parallel arrays. */
    }

    part def <fma64782> DenseRegularElasticTissue :> RegularConnectiveTissue {
        doc /* Regular connective tissue, which consists of fibroblasts and of intercellular matrix, which contains elastic fiber bundles oriented predominantly in definable directions. */
    }

    part def <fma69065> EndoEpithelium :> PortionOfEpithelium {
        doc /* Epithelium that derives from endoderm. Examples: urothelium, transitional epithelium of ureter, epithelium of prostatic gland. */
    }
    part def <fma68468> EpitheliumOfGlandOfSmallIntestine :> RegionOfEpitheliumOfSmallIntestine;
    part def <fma63067> EpitheliumOfZoneOfEsophagus :> NonkeratinizingStratifiedSquamousEpithelium;
    part def <fma63634> EpitheliumOfZoneOfSmallIntestine :> EndoEpithelium;
    part def <fma63629> EpitheliumOfZoneOfStomach :> MicrovillusColumnarEpithelium;

    part def <fma64800> GlandularColumnarEpithelium :> SimpleColumnarEpithelium {
        doc /* Simple columnar epithelium that constitutes the secretory part of a gland. Examples: epithelium of stomach, luminal epithelium of lactiferous duct. */
    }

    part def <fma20107> IrregularConnectiveTissue :> PortionOfConnectiveTissue {
        doc /* Connective tissue, which consists of a population of connective tissue cells, the intercellular matrix of which contains an irregular network of collagen and elastic fiber bundles. Examples: areolar tissue, mucoid tissue, connective tissue of peritoneum, connective tissue of fibrous pericardium. */
    }

    part def <fma19783> LooseConnectiveTissue :> IrregularConnectiveTissue {
        doc /* Irregular connective tissue, the intercellular matrix of which contains a sparse irregular network of collagen and elastic fiber bundles. Examples: areolar tissue, neuroglial tissue, mucoid tissue. */
    }

    part def <fma86452> MesoEpithelium :> PortionOfEpithelium {
        doc /* Epithelium that derives from mesoderm. Examples: endothelium of artery, mesothelium of pleura */
    }

    part def <fma14074> Mesothelium :> MesoEpithelium {
        doc /* Simple squamous epithelium of mesodermal origin which lines serous membranes. Examples: mesothelium of pleura, mesothelium of peritoneum. */
    }
    part def <fma263364> MesotheliumOfRegionOfVisceralPeritoneum :> Mesothelium;

    part def <fma64799> MicrovillusColumnarEpithelium :> SimpleColumnarEpithelium {
        doc /* Simple columnar epithelium in which the luminal side of the cells bears microvilli. Examples: epithelium of small intestine, epithelium of gall bladder. */
    }

    part def <fma45562> MultilaminarEpithelium :> PortionOfEpithelium {
        doc /* Epithelium which consists of more than one layer of epithelial cells that may or may not be in contact with a basement membrane. Examples: keratinized stratified squamous epithelium, ciliated stratified columnar epithelium. */
    }
    part def <fma68413> MuscularisMucosae :> SmoothMuscleTissue;
    part def <fma83556> MuscularisMucosaeOfSegmentOfEsophagus :> MuscularisMucosae;
    part def <fma83558> MuscularisMucosaeOfZoneOfSmallIntestine :> MuscularisMucosae;
    part def <fma83557> MuscularisMucosaeOfZoneOfStomach :> MuscularisMucosae;

    part def <fma45569> NonkeratinizingStratifiedSquamousEpithelium :> StratifiedSquamousEpithelium {
        doc /* Stratified squamous epithelium is a stratified squamous epithelium, the cells of which synthesizes but does not accumulate keratin. Examples: epithelium of vagina, epithelium of wall of esophagus. */
    }

    part def <fma9640> PortionOfConnectiveTissue :> PortionOfTissue {
        doc /* Tissue which consists of fibroblasts, osteocytes or chondrocytes and intercellular matrix produced by these cells. Examples: bone (tissue), dense regular elastic tissue, areolar tissue, neuroglia, adipose tissue. */
    }

    part def <fma9639> PortionOfEpithelium :> PortionOfTissue {
        doc /* Portion of tissue, which consists of one or more layers of epithelial cells and a basement membrane; it covers the external surface of the body and lines the internal surfaces of the anatomical structures. Examples: simple squamous epithelium, glandular cuboidal epithelium, transitional epithelium, myoepithelium. */
    }

    part def <fma9641> PortionOfMuscleTissue :> PortionOfTissue {
        doc /* Portion of tissue which has as its parts an aggregate of muscle cells surrounded by a reticulum of collagen fibers or fine connective tissue [endomysium]. Examples: Smooth muscle tissue, Cardiac muscle tissue. */
    }

    part def <fma9637> PortionOfTissue :> PostnatalAnatomicalStructure {
        doc /* Anatomical structure, each instance of which has as its parts some cells of predominantly one type with or without intercellular matrix. Examples: portion of epithelium, portion of muscle tissue, portion of connective tissue, portion of neural tissue. */
    }
    part def <fma68480> RegionOfEpitheliumOfSmallIntestine :> EndoEpithelium;

    part def <fma20103> RegularConnectiveTissue :> PortionOfConnectiveTissue {
        doc /* Connective tissue, which consists of fibroblasts, the intercellular matrix of which contains a regular network of collagen and elastic fiber bundles. Examples: bone (tissue), cartilage (tissue), dense regular collagenous tissue. */
    }

    part def <fma45567> SimpleColumnarEpithelium :> UnilaminarEpithelium {
        doc /* Unilaminar epithelium, which consists of a single layer of columnar cells. Examples: ciliated columnar epithelium, gastric epithelium, microvillus columnar epithelium. */
    }

    part def <fma14070> SmoothMuscleTissue :> PortionOfMuscleTissue {
        doc /* Tissue which consists of smooth muscle fibers surrounded by a reticulum of collagen and elastic fibers. Examples: Arrector muscle of hair, Muscularis mucosae. */
    }

    part def <fma45563> StratifiedSquamousEpithelium :> MultilaminarEpithelium {
        doc /* Multilaminar epithelium which consists of more than one layer of squamous cells only one layer of which is in contact with a basement membrane. Examples: keratinized stratified squamous epithelium, epithelium of wall of esophagus. */
    }

    part def <fma45561> UnilaminarEpithelium :> PortionOfEpithelium {
        doc /* Epithelium which consists of a single layer of epithelial cells. Examples: endothelium, mesothelium, glandular squamous epithelium. */
    }
}
