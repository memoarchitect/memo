// operational viewpoint.
//
// This project does not define its own viewpoint here; it binds the reusable
// MEMO viewpoint that frames these concerns. The views it governs sit beneath
// `views/`.
package memo_examples_gastric_bypass_variants_viewpoints_operational {
    public import memo_viewpoints_operational_operational_viewpoint::*;
}
