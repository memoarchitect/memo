package memo_examples_gpca_pump_viewpoints_cybersecurity_views_document_threat_model_view {
    private import memo::*;
    private import ScalarValues::*;


    view threatModelView : MemoCybersecurityThreatModelView {
        expose memo_examples_gpca_pump_viewpoints_cybersecurity_views_document_threat_model_view::*;
        @MemoIdentity { :>> providedId = "DOC-002"; :>> label = "GPCACyberThreatModelView"; :>> shortDescription = "Threat-model-oriented document view for GPCA."; }
        doc /* Captures GPCA cyber assets, trust boundaries, threats, threat scenarios, vulnerabilities, and mitigations for secure product development records. */
        attribute :>> version = "0.1.0";
        attribute :>> lifecycleState = LifecycleStateKind::development;
        attribute :>> marketScope = "generic";
        ref :>> viewpointDefinition = cybersecurityViewpoint;
        part :>> selectionQuery {
            @MemoIdentity { :>> providedId = "QRY-DOC-008"; :>> label = "Threat model view query"; }
            attribute :>> includeElementKinds = ("Threat", "OperativeScenario", "Vulnerability", "CybersecurityAsset", "TrustBoundary", "AttackSurface", "CyberMitigation", "SecurityRequirement");
            attribute :>> includeRelationshipKinds = ("ThreatenedBy", "Exploits", "RealizedByScenario", "CrossesTrustBoundary", "Mitigates", "DerivesCyberRequirement");
            attribute :>> rationaleText = "Declares what this document-backed view renders; the web renderer is presentation-only.";
        }
    }
}
