// risk viewpoint.
//
// This project does not define its own viewpoint here; it binds the reusable
// MEMO viewpoint that frames these concerns. The views it governs sit beneath
// `views/`.
package memo_examples_gpca_pump_viewpoints_risk {
    public import memo_viewpoints_risk_risk_viewpoint::*;
}
