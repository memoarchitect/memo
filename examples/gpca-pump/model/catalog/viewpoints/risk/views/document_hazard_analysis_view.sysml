package memo_examples_gpca_pump_viewpoints_risk_views_document_hazard_analysis_view {
    private import memo::*;
    private import ScalarValues::*;

    private import memo_examples_gpca_pump_gpca_analysis::*;

    view hazardAnalysisView : MemoDocumentView {
        expose memo_examples_gpca_pump_viewpoints_risk_views_document_hazard_analysis_view::*;
        expose fmeaDelivery;
        expose ftaOverdose;
        @MemoIdentity { :>> providedId = "DOC-009"; :>> label = "Hazard analysis report view"; :>> shortDescription = "Hazard analysis report aligned to the UMN CriSys GPCA hazard tables."; }
        doc /* Aggregates the five hazard chains, the FMEA worksheet, and the overdose fault tree with their controls and verification pointers. */
        attribute :>> version = "0.1.0";
        attribute :>> lifecycleState = LifecycleStateKind::development;
        attribute :>> viewKind = DocumentViewKind::RMF;
        attribute :>> generationRule = "Include hazards, sequences of events, situations, harms, FMEA rows, fault tree, and controls";
        attribute :>> marketScope = "generic";
        ref :>> viewpointDefinition = riskViewpoint;
        part :>> selectionQuery {
            @MemoIdentity { :>> providedId = "QRY-DOC-003"; :>> label = "Hazard analysis view query"; }
            attribute :>> includeElementKinds = ("FMEAWorksheet", "FailureMode", "FailureCause", "FailureEffect", "DetectionMethod", "FMEAAction", "FaultTree", "FaultTreeNode", "MinimalCutSet", "Hazard", "HazardCause", "SequenceOfEvents");
            attribute :>> includeRelationshipKinds = ("HasFailureMode", "Causes", "DetectedBy", "Mitigates", "InputToGate", "ContainsEvent");
            attribute :>> rationaleText = "Declares what this document-backed view renders; the web renderer is presentation-only.";
        }
    }
}
