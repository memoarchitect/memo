package memo_examples_gpca_pump_viewpoints_functional_views_functional_function_browser_view {
    private import memo::*;
    private import ScalarValues::*;


    view gpcaFunctionBrowserView : MemoDiagramView {
        expose memo_examples_gpca_pump_viewpoints_functional_views_functional_function_browser_view::*;
        attribute depth = 2;
        @MemoIdentity { :>> providedId = "VIEW-FUN-103"; :>> label = "GPCA_FunctionBrowserView"; :>> shortDescription = "Membership tree over the functions layer: logical functions, flows, and the exchange item definitions, grouped by kind."; }
        doc /* Browser view (SysML v2 browser view kind) exposing the functions-layer membership hierarchy as a first-class view: the eleven logical functions, the logical flows connecting them, and the data/control definitions they exchange — with kind icons, expand/collapse, and filtering. */
        attribute :>> outputKind = (ViewOutputKind::diagram);
        attribute :>> presentationKind = (PresentationKind::blockDiagram);
        attribute :>> viewKind = DiagramViewKind::browser;
        attribute :>> dataSourceDescription = "GPCA logical functions, flows, and exchange item definitions";
        attribute :>> autoPopulate = true;
        attribute :>> queryDescription = "Include the functions layer's functions, flows, and exchange item definitions.";
        part :>> selectionQuery {
            @MemoIdentity { :>> providedId = "QRY-FUN-103"; :>> label = "GPCA_FunctionBrowserQuery"; }
            // No "FunctionalExchange": an exchange is a flow between two
            // functions, not an element, so it is drawn as the edge between
            // the selected functions rather than selected by kind.
            attribute :>> includeElementKinds = ("SystemFunction", "InterfaceItem");
            attribute :>> includeLayers = ("functions");
            attribute :>> selectionExpression = "product == 'GPCA'";
            attribute :>> rationaleText = "Auto-populate the function browser from the functions layer.";
        }
        ref :>> viewpointDefinition = functionalViewpoint;
    }
}
