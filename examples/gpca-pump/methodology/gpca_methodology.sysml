// The GPCA methodology package.
//
// A resolved methodology is derived from the project binding and the methodology
// chain, so nothing is connected here: see `model/catalog/gpca_project.sysml` for the
// binding, and `gpca_profiles.sysml` for the methodology it selects.
package memo_examples_gpca_pump_methodology_gpca_methodology {
    private import memo_examples_gpca_pump_methodology_gpca_profiles::*;
}
